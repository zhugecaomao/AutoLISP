(defun c:2hgstyle ()
(menucmd "s=sel")
(setq t (getvar "textstyle"))
(setq l (getstring "Input change after text style = "))
(command "style" l l "" "" "" "" "" "")
(setq a (ssget))
(setq b (sslength a))
(setq d 0)
(repeat b
(setq c (ssname a d))
(setq q (entget c))
(setq e (assoc 7 (entget c)))
(setq k (cdr (assoc 0 (entget c))))
(if (= k "TEXT")
(progn
(setq f (subst (cons 7 l) e q))
(entmod f))
)
(setq d (+ d 1))
)
(command "style" t t "" "" "" "" "" "")
(princ)
)

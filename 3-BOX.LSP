(defun c:3-box()
;(IF (= (TYPE F1) 'FILE ) "YES"  (STOP))
;(IF (= (TYPE F2) 'FILE ) "YES" (STOP))
(COMMAND "SETVAR" "HIGHLIGHT" "1")
(setq A(getdist "\n Length:"))
(setq B(getdist "\n Width:"))
(setq C(getdist "\n Thickness:"))
(setq D(getdist "\n Space:"))
(setq P1(getpoint "\n Box center:"))
(setq P2(list (- (car p1) (/ a 2)) (- (cadr p1) (/ b 2))))
(setq P3(list (+ (car p2) a) (cadr p2)))
(setq P4(list (car p3) (+ (cadr p2) b)))
(setq P5(list (+ (car p3) d) (cadr p2)))
(setq P6(list (+ (car p5) c) (cadr p5)))
(setq P7(list (car p6) (cadr p4)))
(setq P8(list (car p5) (cadr p4)))
(setq P9(list (car p2) (- (cadr p2) d)))
(setq P10(list (car p9) (- (cadr p9) c)))
(setq P11(list (car p3) (cadr p10)))
(setq P12(list (car p11) (cadr p9)))
(setq P13(list (car p2) (cadr p4)))
(command "line" p2 p3 p4 p13 "c")
(command "line" p5 p6 p7 p8 "c")
(command "line" p9 p10 p11 p12 "c")
(COMMAND "SETVAR" "HIGHLIGHT" "1")
)

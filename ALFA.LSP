(VMON)(PROMPT "\nplease wait ")(DEFUN   SN nil (PRINC (STRCAT "\nDayu2 System            Serial Number : 77-" (RTOS Qj 2 0) "      VER : 2.0")) (PRINC "\nDeveloped by Software Team Autotech Inc. (C) Copyright Autotech Inc. 1988") (PRINC))(DEFUN *ERROR* (Q@) (IF (= (TYPE QQ) (QUOTE FILE)) (CLOSE QQ)) (SETQ QQ nil) (COMMAND "'redraw") (  MODER) (IF (NULL Ql) (PROGN (PRINC "error: ") (PRINC Q@) (PRINC)) (PROGN (REPEAT Ql (ENTDEL (ENTLAST))) (SETQ Q& Q1 Ql nil) (PRINC))))(DEFUN   MODES (Q#) (SETQ Q0 (QUOTE nil)) (REPEAT (LENGTH Q#) (SETQ Q0 (APPEND Q0 (LIST (LIST (CAR Q#) (GETVAR (CAR Q#)))))) (SETQ Q# (CDR Q#))))(DEFUN   MODER nil (REPEAT (LENGTH Q0) (SETVAR (CAAR Q0) (CADAR Q0)) (SETQ Q0 (CDR Q0))))(PRINC ".")(DEFUN Q$ (Q@) (IF (= (ASCII (SUBSTR Q@ 2 1)) 130) (SETQ Q@ (STRCAT (SUBSTR Q@ 1 1) (CHR (- (ASCII (SUBSTR Q@ 2 1)) 36))))) (IF (= (ASCII (SUBSTR Q@ 2 1)) 128) (SETQ Q@ (STRCAT (SUBSTR Q@ 1 1) (CHR (- (ASCII (SUBSTR Q@ 2 1)) 36))))) (SETQ Q@ Q@))(SETQ Qj 51)(PRINC ".")(DEFUN QO (Q#) (IF (OR (AND (>= Q# 97) (<= Q# 102)) (AND (>= Q# 65) (<= Q# 70)) (AND (>= Q# 48) (<= Q# 57))) (COND ((OR (= Q# 97) (= Q# 65)) (* 10 1)) ((OR (= Q# 98) (= Q# 66)) (* 11 1)) ((OR (= Q# 99) (= Q# 67)) (* 12 1)) ((OR (= Q# 100) (= Q# 68)) (* 13 1)) ((OR (= Q# 101) (= Q# 69)) (* 14 1)) ((OR (= Q# 102) (= Q# 70)) (* 15 1)) (T (- Q# 48))) (PROGN (Q| "error") (SETQ Q% 1))))(PRINC ".")(DEFUN Q?j (Qjj / Q@j QQj Qlj Q&j) (SETQ Q@j (QO (NTH 0 Qjj))) (IF (/= Q% 1) (SETQ QQj (QO (NTH 1 Qjj)))) (IF (/= Q% 1) (SETQ Qlj (QO (NTH 2 Qjj)))) (IF (/= Q% 1) (SETQ Q&j (QO (NTH 3 Qjj)))) (IF (/= Q% 1) (PROGN (SETQ QQj (CHR (+ (* Q@j 16) QQj))) (SETQ Q@j (CHR (+ (* Qlj 16) Q&j))) (STRCAT QQj Q@j)) (PROGN (SETQ Q% nil) (SETQ Q1j ""))))(SETQ Q#j 2.43989000000000E+05)(PRINC ".")(DEFUN   ALFA (Q0j / Q$j QOj Q|j) (SETQ Q$j "" QOj "" Q|j 1) (REPEAT (STRLEN Q0j) (SETQ QOj (SUBSTR Q0j Q|j 1)) (IF (= QOj ";") (SETQ QOj "'")) (SETQ Q$j (STRCAT Q$j QOj)) (SETQ Q|j (+ Q|j 1))) (COND ((= Q$j "U3") (SETQ Q$j "U33")) ((= Q$j "U4") (SETQ Q$j "U44"))) (MENUCMD (STRCAT "i=" Q$j)) (MENUCMD "i=*"))(SETQ Q#j (+ Q#j 3000.0))(PRINC ".")(DEFUN Q%j (Q?@ / Qj@) (IF (AND (/= Ql 0) (= Q@@ 0)) (PROGN (QQ@ 0) (IF (NULL Ql@) (ENTDEL (ENTLAST)) (SETQ Ql@ nil)) (SETQ Qj@ Q&@) (REPEAT (/ (- (LENGTH Qj@) 1) 2) (SETQ Qj@ (CDR Qj@)) (SETQ Qj@ (CDR Qj@))) (SETQ Q1@ (CAR Qj@)) (SETQ Q@@ (LENGTH Q1@)) (SETQ Q& (CADR Qj@)) (SETQ Q1 Q&) (IF (= Q#@ 0) (SETQ Q& (POLAR Q& Q0@ (* (+ (* Q$@ QO@) (* Q$@ QO@ Q|@)) (LENGTH (CAR Qj@))))) (SETQ Q& (POLAR Q& Q0@ (* (* Q$@ 1.25) (LENGTH (CAR Qj@)))))) (SETQ Qj@ Q&@) (SETQ Q&@ (QUOTE nil)) (REPEAT (/ (- (LENGTH Qj@) 1) 2) (SETQ Q&@ (APPEND Q&@ (LIST (CAR Qj@)))) (SETQ Qj@ (CDR Qj@)) (SETQ Q&@ (APPEND Q&@ (LIST (CAR Qj@)))) (SETQ Qj@ (CDR Qj@)))) (PROGN (IF (= Q#@ 0) (SETQ Q& (POLAR Q& (+ Q0@ PI) (+ (* Q$@ QO@) (* Q$@ QO@ Q|@)))) (SETQ Q& (POLAR Q& (+ Q0@ PI) (* Q$@ 1.25)))) (QQ@ 0) (ENTDEL (ENTLAST)))) (REPEAT Q@@ (SETQ Q?@ (APPEND Q?@ (LIST (CAR Q1@)))) (SETQ Q1@ (CDR Q1@))) (SETQ Q%@ nil) (SETQ Q1@ Q?@))(SETQ Q#j (* (+ Q#j 3000) 4.0))(PRINC ".")(DEFUN Q?Q nil (QQ@ 0) (IF (/= QjQ 1) (PROGN (SETQ Q&@ (APPEND Q&@ (LIST Q1@ Q1))) (SETQ Q& (POLAR Q1 (- Q0@ (/ PI 2.0)) (* Q$@ 1.7    ))) (SETQ Q1 Q&) (SETQ Q@@ 0 Q1@ (QUOTE nil) Q@Q "" Q|j nil))) (SETQ Q%@ nil) (* 1 1))(PRINC ".")(DEFUN QQQ (/ QlQ Q@Q) (REPEAT Ql (ENTDEL (ENTLAST))) (REPEAT (/ (LENGTH Q&@) 2) (SETQ Q@Q "") (SETQ QlQ (CAR Q&@)) (REPEAT (LENGTH QlQ) (SETQ Q@Q (STRCAT Q@Q (CAR QlQ))) (SETQ QlQ (CDR QlQ))) (SETQ Q&@ (CDR Q&@)) (COND ((= Q&Q 1) (Q1Q)) ((= Q&Q 2) (Q#Q)) ((= Q&Q 3) (Q0Q)) ((= Q&Q 4) (Q$Q)) ((= Q&Q 5) (QOQ)) ((= Q&Q 6) (Q|Q))) (SETQ Q&@ (CDR Q&@))) (SETQ Q%@ nil Ql nil))(SETQ Qj (+ Q#j Qj))(PRINC ".")(DEFUN QQ@ (Q%Q) (IF (= Q%Q 1) (PROGN (GRDRAW Q& Q?l 7) (GRDRAW Q?l Qjl 7) (GRDRAW Qjl Q@l 7) (GRDRAW Q@l Q& 7)) (PROGN (GRDRAW QQl Q?l -1) (GRDRAW Q?l Qjl -1) (GRDRAW Qjl Q@l -1) (GRDRAW Q@l QQl -1) (SETQ QQl Q&))))(PRINC ".")(DEFUN Qll (Q&Q / Q&l QOj) (SETQ Q&l Q$@) (SETQ Q$@ (* Q$@ 1.1)) (IF (= Q&Q 1) (PROGN (SETQ QOj Q&) (SETQ Q& (LIST (- (CAR Q&) (* (/ Q$@ 2.0) QO@)) (+ (CADR Q&) (* Q$@ 0.05)))) (SETQ Q?l (POLAR Q& (- (+ Q0@ (/ PI 2.0)) Q1l) (* Q$@ QO@))) (SETQ Qjl (POLAR Q?l (- Q0@ Q1l) Q$@)) (SETQ Q@l (POLAR Q& (- Q0@ Q1l) Q$@)) (QQ@ 1) (SETQ Q%@ 1 QQl Q&) (SETQ Q& QOj)) (PROGN (SETQ Q?l (POLAR Q& Q0@ (* Q$@ QO@))) (SETQ Qjl (POLAR Q?l (- (+ Q0@ (/ PI 2.0)) Q1l) Q$@)) (SETQ Q@l (POLAR Q& (- (+ Q0@ (/ PI 2.0)) Q1l) Q$@)) (QQ@ 1) (SETQ Q%@ 1 QQl Q&))) (SETQ Q$@ Q&l))(PRINC ".")(DEFUN Q#l nil (IF (NULL Q%@) (PROGN (IF (= Q#@ 1) (Qll 1) (Qll 0))) (PROGN (QQ@ 0) (IF (= Q#@ 1) (Qll 1) (Qll 0)))))(PRINC ".")(DEFUN Q1Q nil (IF (= Q0l 0) (COMMAND "text" (CAR Q&@) Q$@ Q$l Q@Q) (COMMAND "text" (CAR Q&@) Q$l Q@Q)))(DEFUN Q#Q nil (SETQ QOl (POLAR (CAR Q&@) Q0@ Q|l)) (COMMAND "text" "a" (CAR Q&@) QOl Q@Q))(DEFUN Q0Q nil (IF (= Q0l 0) (COMMAND "text" "c" (CAR Q&@) Q$@ Q$l Q@Q) (COMMAND "text" "c" (CAR Q&@) Q$l Q@Q)))(DEFUN Q$Q nil (SETQ QOl (POLAR (CAR Q&@) Q0@ Q|l)) (IF (= Q0l 0) (COMMAND "text" "f" (CAR Q&@) QOl Q$@ Q@Q) (COMMAND "text" "f" (CAR Q&@) QOl Q@Q)))(DEFUN QOQ nil (IF (= Q0l 0) (COMMAND "text" "m" (CAR Q&@) Q$@ Q$l Q@Q) (COMMAND "text" "m" (CAR Q&@) Q$l Q@Q)))(DEFUN Q|Q nil (IF (= Q0l 0) (COMMAND "text" "r" (CAR Q&@) Q$@ Q$l Q@Q) (COMMAND "text" "r" (CAR Q&@) Q$l Q@Q)))(PRINC ".")(DEFUN Q%l nil (SETQ Q&Q 1) (COND ((= Q& "Center") (PROGN (SETQ Q&Q 3) (SETQ Q& (GETPOINT "\nCenter point:")))) ((= Q& "Middle") (PROGN (SETQ Q&Q 5) (SETQ Q& (GETPOINT "\nMiddle point:")))) ((= Q& "Right") (PROGN (SETQ Q&Q 6) (SETQ Q& (GETPOINT "\nEnd point:"))))) (SETQ Q1 Q&) (IF (= Q0l 0) (PROGN (SETQ Q$@ (GETDIST Q& (STRCAT "\nHeight <" (RTOS (GETVAR "textsize")) ">: "))) (IF (= Q$@ nil) (SETQ Q$@ (GETVAR "textsize")))) (SETQ Q$@ Q0l)) (SETVAR "pdsize" (+ (* Q$@ 2) 0.3)) (IF (= Q?& nil) (SETQ Q?& 0)) (SETQ Q$l (GETANGLE Q& (STRCAT "\nRotation angle <" (RTOS Q?&) ">: "))) (SETQ Q0@ Q$l) (IF (= Q$l nil) (PROGN (SETQ Q$l Q?&) (SETQ Q0@ (* (/ Q$l 180.0) PI))) (PROGN (SETQ Q$l (* (/ Q$l PI) 180.0)) (SETQ Q?& Q$l))) (IF (= Q#@ 1) (PROGN (SETQ Q0@ (+ Q0@ (- (/ PI 2.0)))) (SETQ Q$l (+ Q$l (- 90))))) (SETQ Qj& nil))(PRINC ".")(DEFUN Q@& (/ QOj) (SETQ Q&Q 2) (SETQ QOj Q&) (SETQ Q& (GETPOINT "\nFirst text line point:")) (SETQ QOl (GETPOINT Q& "\nSecond text line point:")) (SETQ Q1 Q&) (IF (= QOj "Align") (PROGN (SETQ Q$@ (GETVAR "textsize")) (SETVAR "pdsize" (+ (* Q$@ 2) 0.3))) (PROGN (SETQ Q&Q 4) (IF (= Q0l 0) (PROGN (SETQ Q$@ (GETDIST Q& (STRCAT "\nHeight <" (RTOS (GETVAR "textsize")) ">: "))) (IF (= Q$@ nil) (SETQ Q$@ (GETVAR "textsize")))) (SETQ Q$@ Q0l)) (SETVAR "pdsize" (+ (* Q$@ 2) 0.3)))) (SETQ Q$l (ANGLE Q& QOl)) (SETQ Q|l (DISTANCE Q& QOl)) (SETQ Q0@ Q$l) (SETQ Q$l (* (/ Q$l PI) 180.0)) (SETQ Q?& Q$l) (SETQ Qj& nil))(PRINC ".")(DEFUN QQ& (/ Q$j) (WHILE (/= (SETQ Ql& (CADR (GRREAD))) 13) (IF (NUMBERP Ql&) (PROGN (PRINC (CHR Ql&)) (IF (NULL Qjj) (SETQ Qjj (APPEND Qjj (LIST Ql&))) (PROGN (IF (/= Ql& 8) (SETQ Qjj (APPEND Qjj (LIST Ql&))) (PROGN (SETQ Q$j (QUOTE nil)) (SETQ Q&& (LENGTH Qjj)) (REPEAT (- Q&& 1) (SETQ Q$j (APPEND Q$j (LIST (CAR Qjj)))) (SETQ Qjj (CDR Qjj))) (SETQ Qjj Q$j)))))))))(PRINC ".")(DEFUN C:CTEXT (/ Q1& Q#&) (GRAPHSCR) (  MODES (QUOTE ("cmdecho" "blipmode" "highlight"))) (SETVAR "cmdecho" 0) (SETVAR "pdmode" 65) (SETVAR "highlight" 0) (SETQ Q0& T QjQ 0 Q@@ 0 Q1@ (QUOTE nil) Q|j nil Q&@ (QUOTE nil) Ql 0 Q%@ nil) (SETQ Q#& (TBLSEARCH "style" (GETVAR "textstyle"))) (SETQ Q#@ (CDR (ASSOC 70 Q#&))) (SETQ QO@ (CDR (ASSOC 41 Q#&))) (SETQ Q1l (CDR (ASSOC 50 Q#&))) (SETQ Q0l (CDR (ASSOC 40 Q#&))) (SETQ Q1& (CDR (ASSOC 4 Q#&))) (COND ((= (STRCASE Q1&) "DAYUS") (SETQ Q|@ 0.3133)) ((= (STRCASE Q1&) "DAYUM") (SETQ Q|@ 0.3329)) ((= (STRCASE Q1&) "DAYUL") (SETQ Q|@ 0.400875))) (IF (/= (- Q#@ (* 16 (/ Q#@ 16))) 4) (SETQ Q#@ 0) (SETQ Q#@ 1)) (IF (= Q#@ 0) (PROGN (INITGET "Align Center Fit Middle Right \013") (SETQ Q& (GETPOINT "\nStart point or Align/Center/Fit/Middle/Right:"))) (PROGN (INITGET "Align Center Middle Right \013") (SETQ Q& (GETPOINT "\nStart point or Align/Center/Middle/Right:")))) (COND ((= (TYPE Q&) (QUOTE LIST)) (Q%l)) ((= Q& "Align") (Q@&)) ((= Q& "Center") (Q%l)) ((= Q& "Fit") (Q@&)) ((= Q& "Middle") (Q%l)) ((= Q& "Right") (Q%l)) ((NULL Q&) (SETQ Q& Q$&))) (WHILE Q0& (SETVAR "blipmode" 0) (Q#l) (SETQ Qjj (QUOTE nil)) (MENUCMD "I=ERROR") (PRINC "Alfa Code : ") (QQ&) (IF (NULL Qjj) (SETQ QjQ (+ QjQ (Q?Q))) (SETQ QjQ 0)) (IF (= QjQ 2) (SETQ Q0& nil) (PROGN (IF (/= QjQ 1) (PROGN (IF (/= (NTH 0 Qjj) 8) (PROGN (COND ((= (CAR Qjj) 64) (PROGN (IF (= (LENGTH Qjj) 2) (SETQ Q1j (CHR (CAR (CDR Qjj)))) (SETQ Q1j (Q?j (CDR Qjj)))))) (T (PROGN (SETQ Q0j "") (REPEAT (LENGTH Qjj) (SETQ Q0j (STRCAT Q0j (CHR (CAR Qjj)))) (SETQ Qjj (CDR Qjj))) (SETQ Q1j (Q$ (GETSTRING (  ALFA (STRCASE Q0j)))))))) (IF (/= Q1j "") (PROGN (IF (= Q1j " ") (SETQ Q1j "¡@")) (IF (= Q0l 0) (COMMAND "text" Q& Q$@ Q$l Q1j) (COMMAND "text" Q& Q$l Q1j)) (IF (= Q#@ 0) (SETQ Q& (POLAR Q& Q0@ (+ (* QO@ Q$@) (* Q$@ QO@ Q|@)))) (SETQ Q& (POLAR Q& Q0@ (* Q$@ 1.25)))) (SETQ QO& Q&) (SETQ Q1@ (APPEND Q1@ (LIST Q1j))) (SETQ Q@@ (+ Q@@ 1)) (SETQ Ql (+ Ql 1))))) (PROGN (SETQ Q?@ (QUOTE nil)) (SETQ Q@@ (- Q@@ 1)) (IF (NULL Q1@) (SETQ Ql@ 1)) (IF (< Q@@ 0) (SETQ Q@@ 0)) (IF (/= Ql@ 1) (SETQ Ql (- Ql 1))) (IF (< Ql 0) (SETQ Ql 0) (PROGN (IF (AND (NULL Q1@) (= Ql 0)) (PROGN (SETQ Ql 1) (SETQ Ql@ 1))) (SETQ Q1@ (Q%j Q?@))))))))))) (QQQ) (SETQ Q$& Q&) (  MODER) (PRINC))(PRINC ".")(DEFUN Q|& (Q%& / Q?1) (SETQ Q?1 (QUOTE nil) Qj1 1) (REPEAT (STRLEN Q%&) (SETQ Q?1 (APPEND Q?1 (LIST (ASCII (SUBSTR Q%& Qj1 1))))) (SETQ Qj1 (1+ Qj1))) (SETQ Q?1 Q?1))(PRINC ".")(DEFUN C:CHGTXT (/ Q@1 QQ1 Ql1 Q&1 Q0& Q@@ Q11 Q#1 Q01 Q$1 QO1 Q@ Q|1 Qj1) (SETQ Q@1 "" Ql1 "" Q0& T) (SETQ Q@@ 0 Q11 (SSGET)) (IF Q11 (PROGN (WHILE Q0& (SETQ Q&1 (GETSTRING "\nOld string: " T)) (IF (= Q&1 "") (SETQ Q0& nil) (PROGN (IF (/= (SUBSTR Q&1 1 1) "@") (PROGN (SETQ Q&1 (Q$ (GETSTRING (  ALFA Q&1)))) (SETQ Ql1 (STRCAT Ql1 Q&1))) (PROGN (IF (= (STRLEN Q&1) 2) (PROGN (SETQ Q1j (SUBSTR Q&1 2 1)) (IF (= Q1j " ") (SETQ Q1j "¡@"))) (SETQ Q1j (Q?j (Q|& (STRCASE (SUBSTR Q&1 2 (- (STRLEN Q&1) 1))))))) (SETQ Ql1 (STRCAT Ql1 Q1j))))))) (SETQ Q&1 Ql1) (SETQ Q%1 (STRLEN Q&1)) (SETQ Q0& T) (WHILE Q0& (SETQ QQ1 (GETSTRING "\nNew string: " T)) (IF (= QQ1 "") (SETQ Q0& nil) (PROGN (IF (/= (SUBSTR QQ1 1 1) "@") (PROGN (SETQ QQ1 (Q$ (GETSTRING (  ALFA QQ1)))) (SETQ Q@1 (STRCAT Q@1 QQ1))) (PROGN (IF (= (STRLEN QQ1) 2) (PROGN (SETQ Q1j (SUBSTR QQ1 2 1)) (IF (= Q1j " ") (SETQ Q1j "¡@"))) (SETQ Q1j (Q?j (Q|& (STRCASE (SUBSTR QQ1 2 (- (STRLEN QQ1) 1))))))) (SETQ Q@1 (STRCAT Q@1 Q1j))))))) (SETQ QQ1 Q@1) (SETQ Q?# (STRLEN QQ1)) (SETQ Qj1 0) (REPEAT (SSLENGTH Q11) (IF (= "TEXT" (CDR (ASSOC 0 (SETQ Q#1 (ENTGET (SSNAME Q11 Qj1)))))) (PROGN (SETQ Q0& nil Q|1 1) (SETQ Q01 (CONS 1 (SETQ Q$1 (CDR (ASSOC 1 Q#1))))) (WHILE (= Q%1 (SETQ QO1 (STRLEN (SETQ Q@ (SUBSTR Q$1 Q|1 Q%1))))) (IF (= Q@ Q&1) (PROGN (SETQ Q$1 (STRCAT (SUBSTR Q$1 1 (1- Q|1)) QQ1 (SUBSTR Q$1 (+ Q|1 Q%1)))) (SETQ Q0& T) (SETQ Q|1 (+ Q|1 Q?#))) (SETQ Q|1 (1+ Q|1)))) (IF Q0& (PROGN (SETQ Q#1 (SUBST (CONS 1 Q$1) Q01 Q#1)) (ENTMOD Q#1) (SETQ Q@@ (1+ Q@@)))))) (SETQ Qj1 (1+ Qj1))))) (PRINC "Changed ") (PRINC Q@@) (PRINC " text lines.") (PRINC))(PRINC ".")(DEFUN   TXT (/ Q0& Q1@ Q@Q Qjj Ql& Q$j Q&& Q1j Q0j Q?@) (  MODES (QUOTE ("texteval"))) (SETQ Q0& T Q1@ (QUOTE nil) Q@Q "") (WHILE Q0& (SETQ Qjj (QUOTE nil)) (MENUCMD "I=ERROR") (PROMPT "\nAlfa Code : ") (WHILE (/= (SETQ Ql& (CADR (GRREAD))) 13) (IF (NUMBERP Ql&) (PROGN (PRINC (CHR Ql&)) (IF (NULL Qjj) (SETQ Qjj (APPEND Qjj (LIST Ql&))) (PROGN (IF (/= Ql& 8) (SETQ Qjj (APPEND Qjj (LIST Ql&))) (PROGN (SETQ Q$j (QUOTE nil)) (SETQ Q&& (LENGTH Qjj)) (REPEAT (- Q&& 1) (SETQ Q$j (APPEND Q$j (LIST (CAR Qjj)))) (SETQ Qjj (CDR Qjj))) (SETQ Qjj Q$j)))))))) (IF (NULL Qjj) (SETQ Q0& nil) (PROGN (IF (/= (NTH 0 Qjj) 8) (PROGN (COND ((= (CAR Qjj) 64) (PROGN (IF (= (LENGTH Qjj) 2) (SETQ Q1j (CHR (CAR (CDR Qjj)))) (SETQ Q1j (Q?j (CDR Qjj)))))) (T (PROGN (SETQ Q0j "") (REPEAT (LENGTH Qjj) (SETQ Q0j (STRCAT Q0j (CHR (CAR Qjj)))) (SETQ Qjj (CDR Qjj))) (SETQ Q1j (Q$ (GETSTRING (  ALFA (STRCASE Q0j)))))))) (IF (/= Q1j "") (PROGN (IF (= Q1j " ") (SETQ Q1j "¡@")) (SETQ Q1@ (APPEND Q1@ (LIST Q1j)))))) (PROGN (SETQ Q?@ (QUOTE nil)) (REPEAT (- (LENGTH Q1@) 1) (SETQ Q?@ (APPEND Q?@ (LIST (CAR Q1@)))) (SETQ Q1@ (CDR Q1@))) (SETQ Q1@ Q?@)))))) (REPEAT (LENGTH Q1@) (SETQ Q@Q (STRCAT Q@Q (CAR Q1@))) (SETQ Q1@ (CDR Q1@))) (  MODER) (PRINC Q@Q))(PRINC "Dayu2 System...Loaded")(  SN)(PRINC)

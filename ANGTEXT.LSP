(defun c:at()
        (setq cp (getpoint "\nCENTER PT: "))
      (setq sp (getpoint cp "\nSTART PT :"))
       (setq ep (getpoint cp "\nEND PT: "))
        (setq dis (distance cp sp))
       (setq ang1 (angle cp sp))
       (setq ang2 (angle cp ep))
      (setq ang (abs (- ang1 ang2)))
        (PRINC "\nTEXT HEIGHT <") (PRINC (GETVAR "dimtxt")) (princ ">")
        (if (= (setq hig (getreal)) nil) (setq hig (getvar "dimtxt")))
     (setq atxt (getstring "\nTEXT: "))
     (setq txtlen (strlen atxt))
                (setq angstep (/ ang (- txtlen 1))) (setq num 1)
 (repeat txtlen
        (setq txt (substr atxt num 1))
                        (PRINC "\nANGLE=")(PRINC (angtos ang1 0 2))
     (command "text" sp hig (angtos (- ang1 (DTR 90)) 0 2) txt)
      (setq num (+ 1 num))
       (setq ang1 (- ang1 angstep)) (setq sp (polar cp ang1 dis))
 )
)

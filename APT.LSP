DEFUN C:APT
(SETQ AP (GETVAR "APERTURE"))
(PROMPT"\nnew value for APERTURE<")(PRIN1 AP)(PROMPT">:")
(SETQ AP1 (GETINT))
(IF (= AP1 NIL)
    (SETQ AP1 AP)
)
(COMMAND "SETVAR" "APERTURE" AP1)
(SETQ PK (GETVAR "PICKBOX"))
(PROMPT"\nnew value for PICKBOX<")(PRIN1 PK)(PROMPT">:")
(SETQ PK1 (GETINT))
(IF (= PK1 NIL)
    (SETQ PK1 PK)
)
(COMMAND "SETVAR" "PICKBOX" PK1)

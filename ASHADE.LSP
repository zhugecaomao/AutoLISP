(DEFUN C:CAMERA(/ Qj Q@ QQ Ql Q& Q1 Q# Q0 Q$ QO Q| Q% Q?j)(SETQ Qj *ERROR* *ERROR* AS-ERR)(SETQ Q@(A:CMOD))(GRAPHSCR)(SETQ QQ(A:ACQS"Enter camera name"NIL))(SETQ Q1(A:GP3D"Enter target point"))(SETQ Q&(A:GP3D"Enter camera location"))(SETQ Q?j(*(/ 180 PI)(-(ANGLE Q& Q1)1.570796)))(SETQ Q$(/(GETVAR"VIEWSIZE")9.52381))(IF(NULL Qjj)(SETQ Q1(TRANS Q1 1 0)))(COMMAND"insert""camera"Q& Q$ Q$(STRCAT"<<"(RTOS Q?j 2 6))QQ" "(RTOS(CAR Q1)2 6)(RTOS(CADR Q1)2 6)(RTOS(CADDR Q1)2 6))(A:SMOD Q@)(SETQ *ERROR* Qj)(PRINC))(DEFUN C:LIGHT(/ Qj Q@ QQ Ql Q& Q1 Q# Q0 Q$ QO Q@j Q| Q% Q?j)(SETQ Qj *ERROR* *ERROR* AS-ERR)(SETQ Q@(A:CMOD))(GRAPHSCR)(SETQ QQ(A:ACQS"Enter light name"NIL))(SETQ Q0 T)(WHILE Q0(SETQ Q0(STRCASE(SUBSTR(A:ACQS"Point source or Directed""P")1 1)))(COND((= Q0"P")(SETQ Q@j"overhead")(SETQ Ql" ")(SETQ Q1(quote (0 0 0)))(SETQ Q0 NIL))((= Q0"D")(SETQ Q@j"direct")(SETQ Ql"Parallel")(SETQ Q1(A:GP3D"Enter light aim point"))(SETQ Q0 NIL))))(SETQ Q&(A:GP3D"Enter light location"))(SETQ Q$(/(GETVAR"VIEWSIZE")9.52381))(IF(= Q@j"overhead")(SETQ Q?j 0)(SETQ Q?j(*(/ 180 PI)(-(ANGLE Q& Q1)1.570796))))(IF(NULL Qjj)(SETQ Q1(TRANS Q1 1 0)))(COMMAND"insert"Q@j Q& Q$ Q$(STRCAT"<<"(RTOS Q?j 2 6))QQ Ql(RTOS(CAR Q1)2 6)(RTOS(CADR Q1)2 6)(RTOS(CADDR Q1)2 6))(A:SMOD Q@)(SETQ *ERROR* Qj)(PRINC))(DEFUN C:SCENE(/ Qj QQ QQj Qlj Q&j Q1j Q#j Q0j ENAME Q& Q$ Q$j)(SETQ Qj *ERROR* *ERROR* AS-ERR)(SETQ QQ"")(SETQ V:OLST NIL)(GRAPHSCR)(SETQ QQ(A:ACQS"Enter scene name"NIL))(SETQ V:OLST(LIST QQ))(SETQ V:OBJC"CAMERA")(A:BGET(A:SLOB"\nSelect the "": "NIL))(SETQ QQj(CDR(ASSOC(quote 1)(A:EGET"SNAME"))))(PROMPT(STRCAT" "QQj"\n"))(SETQ V:OLST(APPEND V:OLST(LIST(LIST"CAMERA"QQj))))(SETQ V:OBJC"LIGHT")(SETQ Q$j"Lights:")(SETQ Qlj 1)(WHILE(AND QQj Qlj)(SETQ Qlj(A:SLOB"\nSelect a "": "T))(IF Qlj(PROGN(A:BGET Qlj)(SETQ Qlj(CDR(ASSOC(quote 1)(A:EGET"SNAME"))))(PROMPT(STRCAT" "Qlj"\n"))(IF(A:NTIN Qlj)(SETQ V:OLST(APPEND V:OLST(LIST(LIST V:OBJC Qlj)))Q$j(STRCAT Q$j" "Qlj))(PROMPT(STRCAT"\nLight "Qlj" already selected.\n"))))))(IF V:OLST(PROGN(SETQ Q#j(CDR V:OLST))(SETQ Q0j(CADR(ASSOC(quote "CAMERA")Q#j)))(SETQ Q&(A:GP3D"Enter scene location"))(SETQ Q$(/(GETVAR"VIEWSIZE")85.0))(A:CLIN QQ Q& Q$(STRCAT"Camera: "Q0j)Q$j)(A:SINS QQ"CAMERA"Q0j Q& Q$)(FOREACH Q0j Q#j(IF(EQ(CAR Q0j)"LIGHT")(PROGN(SETQ Q&(CONS(+(CAR Q&)(* 0.8 Q$))(CDR Q&)))(A:SINS QQ"LIGHT"(CADR Q0j)Q& Q$))))(PROMPT(STRCAT"\nScene "QQ" included.\n")))(PROMPT"\nNo scenes included.\n"))(SETQ V:OLST NIL)(SETQ *ERROR* Qj)(PRINC))(DEFUN A:SINS(QQ QOj Q0j Q& Q$ / Q@ QO)(SETQ Q@(A:CMOD))(COMMAND"insert""shot"Q& Q$ Q$"<<0"QOj Q0j QQ)(A:SMOD Q@))(DEFUN A:CLIN(QQ Q& Q$ Q|j Q%j / Q@ QO)(SETQ Q@(A:CMOD))(COMMAND"insert""clapper"Q& Q$ Q$"<<0"QQ Q|j Q%j)(A:SMOD Q@))(DEFUN A:SMOD(Q?@ / Qj@ Q@@ QQ@ Ql@)(SETQ Qj@ NIL)(FOREACH Q@@ Q?@(SETQ QQ@(CAR Q@@))(SETQ Ql@(GETVAR QQ@))(SETQ Qj@(APPEND Qj@(LIST(LIST QQ@ Ql@))))(SETVAR QQ@(CADR Q@@)))Qj@)(DEFUN A:CMOD()(A:SMOD(quote (("CMDECHO"0)("LIMCHECK"0)("EXPERT"1)("ORTHOMODE"0)("ATTDIA"0)))))(DEFUN A:ACQS(Q&@ Q1@ / Q#@ Q0@)(SETQ Q#@ NIL Q0@ T)(COND((NULL Q1@)(SETQ Q&@(STRCAT"\n"Q&@": ")))(T(SETQ Q&@(STRCAT"\n"Q&@" <"Q1@">: "))))(WHILE Q0@(SETQ Q#@(GETSTRING Q&@))(IF(OR(NOT(OR(NULL Q#@)(= Q#@"")))Q1@)(SETQ Q0@ NIL)))(SUBSTR(IF(= Q#@"")Q1@ Q#@)1 8))(DEFUN A:SLOB(Q$@ QO@ Q|@ / Q%@)(SETQ Q%@ 1)(WHILE(= 1 Q%@)(SETQ ENAME(CAR(ENTSEL(STRCAT Q$@(STRCASE V:OBJC T)QO@))))(IF ENAME(IF(=(CDR(ASSOC(quote 0)(SETQ Q?Q(ENTGET ENAME))))"INSERT")(PROGN(SETQ QjQ(CDR(ASSOC(quote 2)Q?Q)))(COND((OR(= V:OBJC QjQ)(AND(= QjQ"DIRECT")(= V:OBJC"LIGHT"))(AND(= QjQ"OVERHEAD")(= V:OBJC"LIGHT"))(AND(= QjQ"SHOT")(= V:OBJC"SCENE")))(SETQ Q%@ NIL))(T(PROMPT(STRCAT"\nSelected object is not a "(STRCASE V:OBJC T)" \n"))))))(IF Q|@(SETQ Q%@ NIL))))ENAME)(DEFUN A:BGET(ENAME / Q%@ Q?Q)(SETQ Q%@ 1)(COND((AND(LISTP(quote V:BLST))(= ENAME(CDR(ASSOC(quote -1)(CAR V:BLST)))))(ENAME))(T(SETQ V:BLST(LIST(ENTGET ENAME)))(WHILE Q%@(SETQ Q?Q(ENTGET(SETQ ENAME(ENTNEXT ENAME))))(IF(=(CDR(ASSOC(quote 0)Q?Q))"SEQEND")(SETQ Q%@ NIL)(SETQ V:BLST(APPEND V:BLST(LIST Q?Q)))))(CDR(ASSOC(quote -1)(CAR V:BLST))))))(DEFUN A:EGET(Q@Q / Q?Q Q#j)(SETQ Q?Q NIL)(FOREACH Q#j V:BLST(IF(AND(=(CDR(ASSOC(quote 0)Q#j))"ATTRIB")(=(CDR(ASSOC(quote 2)Q#j))Q@Q))(SETQ Q?Q Q#j)))Q?Q)(DEFUN A:NTIN(Qlj / QQQ QlQ)(SETQ QlQ NIL)(FOREACH QQQ(CDR V:OLST)(IF(AND(EQ"LIGHT"(CAR QQQ))(EQ Qlj(CADR QQQ)))(SETQ QlQ 1)))(NULL QlQ))(DEFUN A:GP3D(Q&Q)(INITGET(+ 1 8 16))(SETVAR"lastpt3d"(GETPOINT(STRCAT"\n"Q&Q": "))))(DEFUN C:CAMVIEW(/ Qj ENAME QQj)(IF(= 1(GETVAR"flatland"))(PROMPT"This routine requires FLATLAND to be set to 0.")(PROGN(SETQ Qj *ERROR* *ERROR* AS-ERR)(SETQ Q@(A:CMOD))(SETQ V:OBJC"CAMERA")(SETQ ENAME(A:BGET(A:SLOB"\nSelect the "": "NIL)))(SETQ QQj(CDR(ASSOC(quote 1)(A:EGET"SNAME"))))(PROMPT(STRCAT" "QQj"\n"))(Q1Q(ENTGET ENAME))(A:SMOD Q@)(SETQ *ERROR* Qj)))(PRINC))(DEFUN Q1Q(Q#Q / Q0Q Q$Q QOQ Q|Q Q%Q Q?l Qjl)(SETQ Q0Q(ENTGET(ENTNEXT(CDR(ASSOC -1 Q#Q)))))(WHILE(AND(=(CDR(ASSOC 0 Q0Q))"ATTRIB")(/=(CDR(ASSOC 0 Q0Q))"SEQEND"))(COND((=(CDR(ASSOC 2 Q0Q))"LAX")(SETQ Q$Q(CDR(ASSOC 1 Q0Q))))((=(CDR(ASSOC 2 Q0Q))"LAY")(SETQ QOQ(CDR(ASSOC 1 Q0Q))))((=(CDR(ASSOC 2 Q0Q))"LAZ")(SETQ Q|Q(CDR(ASSOC 1 Q0Q))))(T))(SETQ Q0Q(ENTGET(ENTNEXT(CDR(ASSOC -1 Q0Q))))))(SETQ Q%Q(TRANS(LIST(ATOF Q$Q)(ATOF QOQ)(ATOF Q|Q))0 1))(SETQ Q?l(TRANS(LIST(CADR(ASSOC 10 Q#Q))(CADDR(ASSOC 10 Q#Q))(CADDDR(ASSOC 10 Q#Q)))(CDR(ASSOC -1 Q#Q))1))(SETQ Qjl(DISTANCE Q?l Q%Q))(COMMAND"dview""""po"Q%Q Q?l"d"Qjl""))(DEFUN AS-ERR(Q@l)(IF(/= Q@l"Function cancelled")(PRINC(STRCAT"\nError: "Q@l)))(A:SMOD Q@)(SETQ *ERROR* Qj)(PRINC))(DEFUN A:SHADE()(PRINC"\n \n \nAutoShade Commands Loaded, errors: ")(PRINC)(SETQ V:OLST NIL))(COND((GETVAR"viewmode")(SETQ Qjj NIL))(T(SETQ Qjj T C:CAMVIEW NIL Q1Q NIL)))(PRINC"\nAutoShade Commands Loaded, errors: ")(SETQ V:OLST NIL)

(defun c:bakhid2 ()
(setvar "osmode" 32)
(setq b (getpoint "First break point :"))
(setq c (getpoint "Second break point :"))
(setvar "osmode" 0)
(prompt "select object: ")
(command "break" pause "f" b c)
(prompt "wich one change : ")
(setq lar (getvar "clayer"))
(command "layer" "s" "3" "")
(command "line" b c "")
(command "layer" "s" lar "")
(princ)
)

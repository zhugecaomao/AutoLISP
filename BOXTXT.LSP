(DEFUN C:BOXTXT()
  (SETQ STR (GETSTRING"\nINPUT STRINGS:"))
  (SETQ SNUM (STRLEN STR))
  (SETQ TXH (GETVAR "TEXTSIZE"))
  (SETQ W ( * TXH 1.4))
  (SETQ L (* TXH SNUM 1.1))
  (SETQ P (GETPOINT "\nInsert point:"))
  (SETQ DR1 (LIST (- (CAR P) (/ L 2)) (- (CADR P)(/ W 2))))
  (SETQ DR2 (LIST (+ (CAR P) (/ L 2)) (- (CADR P)(/ W 2))))
  (SETQ DR3 (LIST (- (CAR P) (/ L 2)) (+ (CADR P)(/ W 2))))
  (SETQ DR4 (LIST (+ (CAR P) (/ L 2)) (+ (CADR P)(/ W 2))))
  (COMMAND "LINE" DR1 DR3 DR4 DR2 "C" )
  (PROMPT"\nTEXT HEIGHT:")(PRIN1 TXH)
  (COMMAND "TEXT" "M" P TXH  "" STR)
)

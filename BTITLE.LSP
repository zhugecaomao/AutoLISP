(Defun C:BTITLE ()(Setvar "Cmdecho" 0)
(Setq F (Getvar "Blipmode")) (Setvar "Blipmode" 0)
(Setq A (Getreal "\nScaling factor: 1= "))
(Setq P1 (Osnap (Getpoint
"\nTouch bottom right corner of drawing: ")"End"))
(Command "Insert" "*/acad-r10/basdwg/l" P1 (/ A 1) "0")
(Setq P2 (List (- (Car P1) (* 95.0 A)) (+ (Cadr p1) (* 32.0 A))))
(Setq P3 (List (- (Car P1) (* 25.0 A)) (+ (Cadr p1) (* 32.0 A))))
(Setq P4 (List (- (Car P1) (* 62.0 A)) (+ (Cadr p1) (* 25.75 A))))
(Setq P5 (List (- (Car P1) (* 80.25 A)) (+ (Cadr p1) (* 19.75 A))))
(Setq P6 (List (- (Car P1) (* 27.25 A)) (+ (Cadr p1) (* 19.75 A))))
(Setq P7 (List (- (Car P1) (* 7.75 A)) (+ (Cadr p1) (* 19.75 A))))
(Setq P8 (List (- (Car P1) (* 70.0 A)) (+ (Cadr p1) (* 13.75 A))))
(Setq P9 (List (- (Car P1) (* 26.0 A)) (+ (Cadr p1) (* 13.75 A))))
(Command "style" "romanc" "" "" "" "" "" "" "")
(Prompt "\n DRAWING TITLE")
(Prompt ":") (SETQ TEXT (Read-line))
(Command "Text" P2 (* 3.5 A) "0" TEXT)
(Prompt "\n MOLD NUMBER")
(Prompt ":") (SETQ TEXT (Read-line))
(Command "Text" P3 (* 2.5 A) "0" TEXT)
(Prompt "\n FIRST MADE FOR")
(Prompt ":") (Setq TEXT (Read-line))
(Command "Text" P4 (* 2.5 A) "0" TEXT)
(Prompt "\n JOB NO")
(Prompt ":") (Setq TEXT (Read-line))
(Command "Text" P5 (* 2.5 A) "0" TEXT)
(Prompt "\n No of SHEET")
(Prompt ":") (Setq TEXT (Read-line))
(Command "Text" "c" P6 (* 2.5 A) "0" TEXT)
(Prompt "\n TOTLE SHEETS")
(Prompt ":") (Setq TEXT (Read-line))
(Command "Text" "C" P7 (* 2.5 A) "0" TEXT)
(Prompt "\n DRAWEN BY")
(Prompt ":") (Setq TEXT (Read-line))
(Command "Text" P8 (* 2.5 A) "0" TEXT)
(Prompt "\n DATE")
(Prompt ":") (Setq TEXT (Read-line))
(Command "Text" P9 (* 2.5 A) "0" TEXT)
(Setvar "Blipmode" F))

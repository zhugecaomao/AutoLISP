(DEFUN C:C1()
(COMMAND "SETVAR" "HIGHLIGHT" "1")
(SETQ P1 (GETPOINT "\nCIRCLE CEND POINT:"))
(SETQ D1 (GETDIST P1 "\nRadius1:"))
(SETQ D2 (GETDIST P1 "\nRadius2:"))
(COMMAND "CIRCLE" P1 D1)
(COMMAND "CIRCLE" P1 D2)
(SETQ CP1 (LIST (CAR P1) (+ (CADR P1) D2 1)))
(SETQ CP2 (LIST (CAR P1) (- (CADR P1) D2 1)))
(SETQ CP3 (LIST (- (CAR P1) D2 1) (CADR P1)))
(SETQ CP4 (LIST (+ (CAR P1) D2 1) (CADR P1)))
(COMMAND "LAYER" "SET" "CENTER" "")
(COMMAND "LINE" CP1 CP2 "")
(COMMAND "LINE" CP3 CP4 "")
(COMMAND "SETVAR" "HIGHLIGHT" "1")
(COMMAND "LAYER" "SET" "0" "")
)

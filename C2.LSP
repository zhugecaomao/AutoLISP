(DEFUN C:C2()
;(IF (= (TYPE F1) 'FILE ) "YES"  (STOP))
;(IF (= (TYPE F2) 'FILE ) "YES" (STOP))
(COMMAND "SETVAR" "HIGHLIGHT" "1")
(SETQ P1 (GETPOINT "\nCIRCLE CEND POINT:"))
(SETQ D1 (GETDIST P1 "\nRadius1:"))
(SETQ D2 (GETDIST P1 "\nRadius2:"))
(SETQ D3 (GETDIST P1 "\nRadius3:"))
(COMMAND "CIRCLE" P1 D1)
(COMMAND "CIRCLE" P1 D2)
(COMMAND "CIRCLE" P1 D3)
(SETQ CP1 (LIST (CAR P1) (+ (CADR P1) D3 1)))
(SETQ CP2 (LIST (CAR P1) (- (CADR P1) D3 1)))
(SETQ CP3 (LIST (- (CAR P1) D3 1) (CADR P1)))
(SETQ CP4 (LIST (+ (CAR P1) D3 1) (CADR P1)))
(COMMAND "LAYER" "SET" "CENTER" "")
(COMMAND "LINE" CP1 CP2 "")
(COMMAND "LINE" CP3 CP4 "")
(COMMAND "SETVAR" "HIGHLIGHT" "1")
(COMMAND "LAYER" "SET" "0" "")
)

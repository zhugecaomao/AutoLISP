(DEFUN VLA ()
   (COMMAND "DIM" "VERT" "" S2 PAUSE (STRCAT "%%C" S3) EXIT)
)
(DEFUN VLB ()
    (COMMAND "DIM" "VERT" S1 S4 PAUSE (STRCAT "%%C" S5) EXIT)
)
(DEFUN C:CLDV ()
   (MENUCMD "S=X")
   (SETQ LP (GETVAR "LUPREC"))
   (SETQ CA (GETVAR "DIMLFAC"))
   (SETQ S1 (GETPOINT "\nFirst extension line origin or RETURN to select:"))
   (SETVAR "CMDECHO" 1)
   (IF (= S1 NIL)
       (PROGN
          (SETQ S2 (ENTSEL "\nSelect line:"))
          (SETQ S3 (- (CADR (CDR (ASSOC 10 (ENTGET (CAR S2)))))
                      (CADR (CDR (ASSOC 11 (ENTGET (CAR S2)))))))
          (SETQ S3 (ABS S3))
          (SETQ S3 (RTOS (* S3 CA) 2 LP))
          (VLA)
          (SETQ S1 NIL) (princ)
       )
   )
   (IF (/= S1 NIL)
       (PROGN
          (SETQ S4 (GETPOINT "\nSecond extension line origin:"))
          (SETQ CA (GETVAR "DIMLFAC"))
          (SETQ LP (GETVAR "LUPREC"))
          (SETQ S5 (ABS (- (CADR S1) (CADR S4))))
          (SETQ S5 (RTOS (* S5 CA) 2 LP))
          (VLB)
       )
    )
   (SETQ S1 NIL) (princ)
)
*----------------------------
   (DEFUN HLA ()
       (COMMAND "DIM" "HORIZ" "" J2 PAUSE (STRCAT "%%C" J3) EXIT)
   )
   (DEFUN HLB ()
       (COMMAND "DIM" "HORIZ" J1 J4 PAUSE (STRCAT "%%C" J5) EXIT)
   )
;-------------------------------------------------------------------------
(DEFUN C:CLDH ()
   (MENUCMD "S=X")
   (SETQ LP (GETVAR "LUPREC"))
   (SETQ CA (GETVAR "DIMLFAC"))
   (SETQ J1 (GETPOINT "\nFirst extension line origin or RETURN to select:"))
   (SETVAR "CMDECHO" 1)
   (IF (= J1 NIL)
       (PROGN
          (SETQ J2 (ENTSEL "\nSelect line:"))
          (SETQ J3 (- (CAR (CDR (ASSOC 10 (ENTGET (CAR J2)))))
                      (CAR (CDR (ASSOC 11 (ENTGET (CAR J2))))) ))
          (SETQ J3 (ABS J3))
          (SETQ J3 (RTOS (* J3 CA) 2 LP))
          (HLA)
          (SETQ J1 NIL) (princ)
       )
   )
   (IF (/= J1 NIL)
       (PROGN
          (SETQ J4 (GETPOINT "\nSecond extension line origin:"))
          (SETQ LP (GETVAR "LUPREC"))
          (SETQ J5 (ABS (- (CAR J1) (CAR J4))))
          (SETQ J5 (RTOS (* CA J5) 2 LP))
          (HLB)
       )
    )
   (SETQ J1 NIL) (princ)
)

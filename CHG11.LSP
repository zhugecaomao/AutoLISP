DEFUN C:CHG11
;SET LAYER
(COMMAND "SETVAR" "CMDECHO" 0)
;(IF (= (TYPE F1) 'FILE ) "YES"  (STOP))
;(IF (= (TYPE F2) 'FILE ) "YES" (STOP))
(setq SET11 (findfile "/acad/hon/SET/SET11.SET"))
(IF (= SET11 NIL)
    (PROGN
       (PROMPT "\nPLEASE SETTING LAYER:" )
       (SETQ FC (OPEN "/acad/hon/SET/SET11.SET" "w"))
       (setq SETL11 (GETSTRING T"\nSETTING LAYER ? <11>:"))
       (IF (OR (= SETL11 "") (= SETL11 NIL))
              (WRITE-LINE "11" FC)
              (WRITE-LINE SETL11 FC)
       )
       (CLOSE FC)
    )
)

(IF (/= SET11 NIL)
    (PROGN
       (SETQ FC (OPEN "/acad/hon/SET/SET11.SET" "r"))
       (SETQ SETL11 (READ-LINE FC))
       (IF (OR (= SETL11 "") (= SETL11 NIL))
           (CLOSE FC)
       )
       (IF (OR (= SETL11 "") (= SETL11 NIL))
           (PROGN
              (PROMPT "\nPLEASE SETTING LAYER:" )
              (SETQ FC (OPEN "/acad/hon/SET/SET11.SET" "w"))
              (setq SETL11 (GETSTRING T"\nSETTING LAYER ? <11>:"))
              (IF (= SETL11 "")
                  (WRITE-LINE "11" FC)
                  (WRITE-LINE SETL11 FC)
              )
           (CLOSE FC)
           )
       )
       (SETQ FC (OPEN "/acad/hon/SET/SET11.SET" "r"))
       (SETQ SETL11 (READ-LINE FC))
       (CLOSE FC)
       (PROMPT "\nLAYER NAME IS:" )(PROMPT SETL11)(TERPRI)
       (COMMAND "LAYER" "S" SETL11 "")
    )
)

(defun c:CHHW (/ ts a n num b1 c c1 d b2)
   (menucmd "p7=number3")
   (menucmd "p7=*")
   (setq ts (getreal "\nENTER NEW TEXT HEIGHT:"))
   (menucmd "p7=metal1")
   (setq a (ssget))
   (setq n (sslength a))
  (setq num 0)
(repeat n
  (setq b1 (entget (ssname a num)))
  (setq num (1+ num))
  (setq c (assoc 40 b1))
  (setq d (cons (car c) TS))
  (setq b2 (subst d c b1))
    (entmod b2)
)
)

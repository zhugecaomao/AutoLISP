(DEFUN C:CHINA ()
   (SETVAR "CMDECHO" 0)
   (SETQ VC (GETVAR "VIEWCTR"))
   (SETQ YR (GETVAR "VIEWSIZE"))
   (SETQ XR (* YR 1.3864))
   (SETQ YD (/ YR 7))
   (SETQ XD (/ XR 8))
   (SETQ XB (- (CAR VC) (/ XR 2)))
   (SETQ YB (- (CADR VC) (/ YR 2)))
   (COMMAND "VSLIDE" "C:/ACAD/SLIDE/CHINA")
;----
   (SETQ PT (GETPOINT "\nPLEASE DIGIT THE CHAR. TABLE : "))
             (SETQ XP (CAR PT))
             (SETQ YP (CADR PT))
             (SETQ XAA (- XP XB))
             (SETQ YAA (- YP YB))
             (SETQ XA (ABS XAA))
             (SETQ YA (ABS YAA))
             (SETQ X (FIX ( / XA XD)))
             (SETQ Y (FIX ( / YA YD)))
;
      (IF (AND (= X 0) (= Y 1))
      (COMMAND "REDRAW" "INSERT" "C:/ACAD/BLOCK/CHINA3" PAUSE 1 1))
      (IF (AND (= X 1) (= Y 1))
      (COMMAND "REDRAW" "INSERT" "C:/ACAD/BLOCK/CHINA3" PAUSE 1 1))
      (IF (AND (= X 3) (= Y 1))
      (COMMAND "REDRAW" "INSERT" "C:/ACAD/BLOCK/CHINA10" PAUSE 1 1))
      (IF (AND (= X 5) (= Y 1))
      (COMMAND "REDRAW" "INSERT" "C:/ACAD/BLOCK/CHINA6" PAUSE 1 1))
      (IF (AND (= X 7) (= Y 1))
      (COMMAND "REDRAW" "INSERT" "C:/ACAD/BLOCK/CHINA8" PAUSE 1 1))
      (IF (AND (= X 0) (= Y 3))
      (COMMAND "REDRAW" "INSERT" "C:/ACAD/BLOCK/CHINA2" PAUSE 1 1))
      (IF (AND (= X 1) (= Y 3))
      (COMMAND "REDRAW" "INSERT" "C:/ACAD/BLOCK/CHINA2" PAUSE 1 1))
      (IF (AND (= X 3) (= Y 3))
      (COMMAND "REDRAW" "INSERT" "C:/ACAD/BLOCK/CHINA9" PAUSE 1 1))
      (IF (AND (= X 5) (= Y 3))
      (COMMAND "REDRAW" "INSERT" "C:/ACAD/BLOCK/CHINA11" PAUSE 1 1))
      (IF (AND (= X 7) (= Y 3))
      (COMMAND "REDRAW" "INSERT" "C:/ACAD/BLOCK/CHINA12" PAUSE 1 1))
      (IF (AND (= X 0) (= Y 5))
      (COMMAND "REDRAW" "INSERT" "C:/ACAD/BLOCK/CHINA1" PAUSE 1 1))
      (IF (AND (= X 1) (= Y 5))
      (COMMAND "REDRAW" "INSERT" "C:/ACAD/BLOCK/CHINA1" PAUSE 1 1))
      (IF (AND (= X 3) (= Y 5))
      (COMMAND "REDRAW" "INSERT" "C:/ACAD/BLOCK/CHINA4" PAUSE 1 1))
      (IF (AND (= X 5) (= Y 5))
      (COMMAND "REDRAW" "INSERT" "C:/ACAD/BLOCK/CHINA5" PAUSE 1 1))
      (IF (AND (= X 7) (= Y 5))
      (COMMAND "REDRAW" "INSERT" "C:/ACAD/BLOCK/CHINA7" PAUSE 1 1))
      )

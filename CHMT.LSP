(VMON)
;(IF (= (TYPE F1) 'FILE ) "YES"  (STOP))
;(IF (= (TYPE F2) 'FILE ) "YES" (STOP))
;-----------------
;Change unit of dimension(in. to mm.)
(DEFUN C:CHMT (/ AC1 AC2 AC3 AC5 AC6)
  (PROMPT "\nIn. to mm.\nSelect old text(s)...")
  (SETQ AC1 (SSGET))
  (SETQ AC3 (SSLENGTH AC1))
  (SETQ AC5 0)
  (WHILE (< AC5 AC3)
      (SETQ AC6 (ENTGET (SSNAME AC1 AC5)))
      (IF (ASSOC 1 AC6)
          (PROGN
           (COND
            ((= (SUBSTR (CDR (ASSOC 1 AC6)) 1 3) "%%C")
             (SETQ AC2 (STRCAT "%%C" (RTOS (* (ATOF (SUBSTR (CDR (ASSOC 1 AC6)) 4)) 25.4) 2 2)))
             (MTT)
            )
            ((= (SUBSTR (CDR (ASSOC 1 AC6)) 1 1) "R")
             (SETQ AC2 (STRCAT "R" (RTOS (* (ATOF (SUBSTR (CDR (ASSOC 1 AC6)) 2)) 25.4) 2 2)))
             (MTT)
            )
            ((/= (ATOF (CDR (ASSOC 1 AC6))) 0)
             (SETQ AC2 (RTOS (* (ATOF (CDR (ASSOC 1 AC6))) 25.4) 2 2))
             (MTT)
            )
           )
           (SETQ AC5 (1+ AC5))
          )
          (SETQ AC5 (1+ AC5))
      )
  ) (PRINC)
)
;
(DEFUN MTT ()
  (SETQ AC6 (SUBST (CONS 1 AC2) (ASSOC 1 AC6) AC6))
  (IF (NULL (ASSOC 62 AC6))
      (SETQ AC6 (CONS (CONS 62 4) AC6))
      (SETQ AC6 (SUBST (CONS 62 4) (ASSOC 62 AC6) AC6))
 )
 (ENTMOD AC6)
)

(defun C:CHSC ()
;(IF (= (TYPE F1) 'FILE ) "YES"  (STOP))
;(IF (= (TYPE F2) 'FILE ) "YES" (STOP))
(COMMAND "SETVAR" "HIGHLIGHT" "1")
(COMMAND "SELECT" "AU" "\\")
(SETQ SA (SSGET "P" ))
;(SETQ SA (SSGET "X" (LIST (CONS 0 "LINE" ))))
(SETQ SCA (GETREAL "\nSCALE OF VALUE:"))
(SETQ N (SSLENGTH SA))                     ;LIST HOW MANY SELECT
(SETQ I 0)
(REPEAT N
(SETQ NA (ENTGET (SSNAME SA I)))
(SETQ I (+ 1 I))
(SETQ NB (ASSOC 0 NA))
(IF (= "TEXT" (CDR NB))
   (PROGN
      (SETQ TP (ASSOC 10 NA))
      (SETQ STY1 (ASSOC 1 NA))
      (SETQ TP1 (CDR TP))
      (SETQ TP2 (LIST (+ (CAR TP1) 2) (+ (CADR TP1) 2)))
      (SETQ STY2 (CDR STY1))
      (SETQ STY3 (RTOS (* (ATOF STY2) SCA) 2 2))
      (command "change" "C" TP1 TP2 "" "" "" "" "" "" STY3)
       )
   )
)
)
(COMMAND "SETVAR" "HIGHLIGHT" "1")

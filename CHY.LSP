(PRINC "\nSelect objects to be changed...\n")
(COMMAND "SETVAR" "HIGHLIGHT" "1")
;(IF (= (TYPE F1) 'FILE ) "YES"  (STOP))
;(IF (= (TYPE F2) 'FILE ) "YES" (STOP))
(COMMAND "SELECT" "AU" "\\")
(SETQ S1 "P")
(setq LA1 (entget (car (entsel"\nSelect Layer To Change:"))))
(SETQ LAB (CDR LA1))
(SETQ LRB (ASSOC 8 LAB))
(SETQ LR (CDR LRB))
(SETVAR "CMDECHO" 0)
(IF S1 (COMMAND "CHANGE" S1 "" "P" "COLOR" "BYLAYER" "LT" "BYLAYER" "LA" LR ""))
(SETVAR "CMDECHO" 1)
(COMMAND "SETVAR" "HIGHLIGHT" "1")

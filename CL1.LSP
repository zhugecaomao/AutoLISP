DEFUN C:CL1
;(IF (= (TYPE F1) 'FILE ) "YES"  (STOP))
;(IF (= (TYPE F2) 'FILE ) "YES" (STOP))
(COMMAND "SETVAR" "HIGHLIGHT" "1")
(SETQ D1 (GETREAL"\nInput Longer 1:"))
(SETQ D2 (GETREAL"\nInput Longer 2:"))
(SETQ ANGC1 (GETANGLE "\nTYPING 1ST ANGLE:"))
(SETQ ANGC2 (GETANGLE "\nTYPING 2ST ANGLE:"))
(SETQ P (GETPOINT "\nWhere Do You Put:"))
(SETQ D11 (* D1 -1))
(SETQ D21 (* D2 -1))
(SETQ P1 (POLAR P ANGC1 D1))
(SETQ P2 (POLAR P ANGC1 D11))
(SETQ P3 (POLAR P ANGC2 D2))
(SETQ P4 (POLAR P ANGC2 D21))
(COMMAND "LINE" P1 P2 "")
(COMMAND "LINE" P3 P4 "")
(COMMAND "SETVAR" "HIGHLIGHT" "1")

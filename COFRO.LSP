;-------------------------
;copy & rotate
(DEFUN C:COFRO (/ SQ1 SN1 P1 P2 SQ2 SN2 SN3)
;(IF (= (TYPE F1) 'FILE ) "YES"  (STOP))
;(IF (= (TYPE F2) 'FILE ) "YES" (STOP))
  (PROMPT "Select Object:")
  (SETQ SN1 (ENTLAST))
  (SETQ SQ1 (SSGET))
  (SETQ P1 (GETPOINT "\nBase point:"))
  (SETQ P2 (GETPOINT P1 "\nNew base point:"))
  (COMMAND "COPY" SQ1 "" P1 P2)
  (SETQ SN2 (ENTLAST))
  (SETQ SQ2 (SSADD))
  (WHILE (NOT (EQUAL SN2 SN1))
    (SETQ SN3 (ENTNEXT SN1))
    (IF (NOT (SSMEMB SN3 SQ1))
        (PROGN
          (SETQ SQ2 (SSADD SN3 SQ2))
          (SETQ SN1 SN3)
        )
        (SETQ SN1 SN3)
    )
  )
  (COMMAND "ROTATE" SQ2 "" P2 PAUSE)
)

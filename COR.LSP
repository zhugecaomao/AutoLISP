(DEFUN C:COR ()
   (SETVAR "CMDECHO" 0)
   (SETQ VC (GETVAR "VIEWCTR"))
   (SETQ YR (GETVAR "VIEWSIZE"))
   (SETQ XR (* YR 1.3864))
   (SETQ YD (/ YR 3))
   (SETQ XD (/ XR 8))
   (SETQ XB (- (CAR VC) (/ XR 2)))
   (SETQ YB (- (CADR VC) (/ YR 2)))
   (COMMAND "VSLIDE" "C:/ACAD/SLIDE/COR")
;----
   (SETQ PT (GETPOINT "\nPLEASE DIGIT THE CHAR. TABLE : "))
             (SETQ XP (CAR PT))
             (SETQ YP (CADR PT))
             (SETQ XAA (- XP XB))
             (SETQ YAA (- YP YB))
             (SETQ XA (ABS XAA))
             (SETQ YA (ABS YAA))
             (SETQ X (FIX ( / XA XD)))
             (SETQ Y (FIX ( / YA YD)))
;
      (IF (AND (= X 0) (= Y 0))
      (COMMAND "REDRAW" "INSERT" "C:/ACAD/BLOCK/COR8" PAUSE 1 1 ))
      (IF (AND (= X 1) (= Y 0))
      (COMMAND "REDRAW" "INSERT" "C:/ACAD/BLOCK/COR10" PAUSE 1 1 ))
      (IF (AND (= X 2) (= Y 0))
      (COMMAND "REDRAW" "INSERT" "C:/ACAD/BLOCK/COR12" PAUSE 1 1))
      (IF (AND (= X 3) (= Y 0))
      (COMMAND "REDRAW" "INSERT" "C:/ACAD/BLOCK/COR14" PAUSE 1 1))
      (IF (AND (= X 4) (= Y 0))
      (COMMAND "REDRAW" "INSERT" "C:/ACAD/BLOCK/COR16" PAUSE 1 1))
      (IF (AND (= X 0) (= Y 1))
      (COMMAND "REDRAW" "INSERT" "C:/ACAD/BLOCK/COR3-5" PAUSE 1 1 ))
      (IF (AND (= X 1) (= Y 1))
      (COMMAND "REDRAW" "INSERT" "C:/ACAD/BLOCK/COR4" PAUSE 1 1))
      (IF (AND (= X 2) (= Y 1))
      (COMMAND "REDRAW" "INSERT" "C:/ACAD/BLOCK/COR4-5" PAUSE 1 1))
      (IF (AND (= X 3) (= Y 1))
      (COMMAND "REDRAW" "INSERT" "C:/ACAD/BLOCK/COR5" PAUSE 1 1))
      (IF (AND (= X 4) (= Y 1))
      (COMMAND "REDRAW" "INSERT" "C:/ACAD/BLOCK/COR5-5" PAUSE 1 1))
      (IF (AND (= X 5) (= Y 1))
      (COMMAND "REDRAW" "INSERT" "C:/ACAD/BLOCK/COR6" PAUSE 1 1))
      (IF (AND (= X 6) (= Y 1))
      (COMMAND "REDRAW" "INSERT" "C:/ACAD/BLOCK/COR6-5" PAUSE 1 1))
      (IF (AND (= X 7) (= Y 1))
      (COMMAND "REDRAW" "INSERT" "C:/ACAD/BLOCK/COR7" PAUSE 1 1))
      (IF (AND (= X 0) (= Y 2))
      (COMMAND "REDRAW" "INSERT" "C:/ACAD/BLOCK/COR1" PAUSE 1 1 ))
      (IF (AND (= X 1) (= Y 2))
      (COMMAND "REDRAW" "INSERT" "C:/ACAD/BLOCK/COR1-2" PAUSE 1 1 ))
      (IF (AND (= X 2) (= Y 2))
      (COMMAND "REDRAW" "INSERT" "C:/ACAD/BLOCK/COR1-3" PAUSE 1 1))
      (IF (AND (= X 3) (= Y 2))
      (COMMAND "REDRAW" "INSERT" "C:/ACAD/BLOCK/COR1-5" PAUSE 1 1))
      (IF (AND (= X 4) (= Y 2))
      (COMMAND "REDRAW" "INSERT" "C:/ACAD/BLOCK/COR1-6" PAUSE 1 1))
      (IF (AND (= X 5) (= Y 2))
      (COMMAND "REDRAW" "INSERT" "C:/ACAD/BLOCK/COR2" PAUSE 1 1))
      (IF (AND (= X 6) (= Y 2))
      (COMMAND "REDRAW" "INSERT" "C:/ACAD/BLOCK/COR2-5" PAUSE 1 1))
      (IF (AND (= X 7) (= Y 2))
      (COMMAND "REDRAW" "INSERT" "C:/ACAD/BLOCK/COR3" PAUSE 1 1))
      )

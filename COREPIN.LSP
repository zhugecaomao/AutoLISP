(defun c:corepin()
(setq F (getvar "blipmode")) (setvar "blipmode" 0)
(setq p1(getpoint "\n Enter up left coner:"))
(setq p2(getpoint "\n Enter up right coner:"))
(setq p3(getpoint "\n Enter bottom point:"))
(setq D (abs (- (car p2) (car p1))))
(if (and (> D 0) (<= D 1.5))
 (progn (setq D1 3.0) (setq H 4.0) (setq D2 4.0)))
(if (and (> D 1.5) (<= D 2.5))
 (progn (setq D1 5.0) (setq H 4.0) (setq D2 6.0)))
(if (and (> D 2.5) (<= D 3.0))
 (progn (setq D1 6.0) (setq H 4.0) (setq D2 7.0)))
(if (and (> D 3.0) (<= D 3.5))
 (progn (setq D1 7.0) (setq H 4.0) (setq D2 8.0)))
(if (and (> D 3.5) (<= D 4.0))
 (progn (setq D1 8.0) (setq H 6.0) (setq D2 9.0)))
(if (and (> D 4.0) (<= D 5.0))
 (progn (setq D1 9.0) (setq H 6.0) (setq D2 10.0)))
(if (and (> D 5.0) (<= D 6.0))
 (progn (setq D1 10.0) (setq H 6.0) (setq D2 11.0)))
(if (and (> D 6.0) (<= D 7.0))
 (progn (setq D1 11.0) (setq H 6.0) (setq D2 12.0)))
(if (and (> D 7.0) (<= D 8.0))
 (progn (setq D1 13.0) (setq H 8.0) (setq D2 14.0)))
(if (and (> D 8.0) (<= D 10.0))
 (progn (setq D1 15.0) (setq H 8.0) (setq D2 16.0)))
(if (and (> D 10.0) (<= D 12.0))
 (progn (setq D1 17.0) (setq H 8.0) (SETQ D2 18.0)))
(if (and (> D 12.0) (<= D 14.0))
 (progn (setq D1 19.0) (setq H 8.0) (setq D2 20.0)))
(if (and (> D 14.0) (<= D 16.0))
 (progn (setq D1 21.0) (setq H 8.0) (setq D2 22.0)))
(if (and (> D 16.0) (<= D 18.0))
 (progn (setq D1 23.0) (setq H 8.0) (setq D2 24.0)))
(if (and (> D 18.0) (<= D 20.0))
 (progn (setq D1 25.0) (setq H 8.0) (setq D2 26.0)))
(if (> (cadr p1) (cadr p3))
 (progn
  (setq p4(list (car p1) (+ (cadr p3) H)))
  (setq p5(list (car p2) (+ (cadr p3) H))))
 (progn
  (setq p4(list (car p1) (- (cadr p3) H)))
  (setq p5(list (car p2) (- (cadr p3) H))))
)
(setq D3 (/ (- D1 D) 2))
(setq D4 (/ (- D2 D) 2))
(setq p6(list (- (car p4) D3) (cadr p4)))
(setq p7(list (- (car p4) D4) (cadr p4)))
(setq p8(list (+ (car p5) D3) (cadr p5)))
(setq p9(list (+ (car p5) D4) (cadr p5)))
(setq p10(list (car p7) (cadr p3)))
(setq p11(list (car p6) (cadr p3)))
(setq p12(list (car p8) (cadr p3)))
(setq p13(list (car p9) (cadr p3)))
(command "line" p1 p4 "")
(command "line" p2 p5 "")
(command "line" p7 p9 "")
(command "line" p7 p10 "")
(command "line" p6 p11 "")
(command "line" p8 p12 "")
(command "line" p9 p13 "")
(setvar "blipmode" F))

defun c:tt
(COMMAND "SETVAR" "CMDECHO" 0)
(COMMAND "LAYER" "MAKE" "0" "COLOR" "7" "0" "LT" "CONTINUOUS" "0" "")
(COMMAND "LAYER" "MAKE" "CEN" "COLOR" "1" "CEN" "LT" "CENTER" "CEN" "")
(COMMAND "LAYER" "MAKE" "HID" "COLOR" "6" "HID" "LT" "HIDDEN" "HID" "")
(COMMAND "LAYER" "MAKE" "DAS" "COLOR" "2" "DAS" "LT" "DASHED" "DAS" "")
(COMMAND "LAYER" "MAKE" "PHA" "COLOR" "4" "PHA" "LT" "PHANTOM" "PHA" "")
(COMMAND "LAYER" "MAKE" "PART1" "COLOR" "7" "PART1" "LT" "CONTINUOUS" "PART1" "")
(COMMAND "LAYER" "MAKE" "PART2" "COLOR" "1" "PART2" "LT" "CENTER" "PART2" "")
(COMMAND "LAYER" "MAKE" "PART3" "COLOR" "6" "PART3" "LT" "HIDDEN" "PART3" "")
(COMMAND "LAYER" "MAKE" "PART4" "COLOR" "4" "PART4" "LT" "PHANTOM" "PART4" "")
(COMMAND "LAYER" "MAKE" "WATER1" "COLOR" "7" "WATER1" "LT" "CONTINUOUS" "WATER1" "")
(COMMAND "LAYER" "MAKE" "WATER2" "COLOR" "1" "WATER2" "LT" "CENTER" "WATER2" "")
(COMMAND "LAYER" "MAKE" "WATER3" "COLOR" "6" "WATER3" "LT" "HIDDEN" "WATER3" "")
(COMMAND "LAYER" "MAKE" "EJC1" "COLOR" "7" "EJC1" "LT" "CONTINUOUS" "EJC1" "")
(COMMAND "LAYER" "MAKE" "EJC2" "COLOR" "1" "EJC2" "LT" "CENTER" "EJC2" "")
(COMMAND "LAYER" "MAKE" "EJC3" "COLOR" "6" "EJC3" "LT" "HIDDEN" "EJC3" "")
(COMMAND "LAYER" "MAKE" "BLT1" "COLOR" "7" "BLT1" "LT" "CONTINUOUS" "BLT1" "")
(COMMAND "LAYER" "MAKE" "BLT2" "COLOR" "1" "BLT2" "LT" "CENTER" "BLT2" "")
(COMMAND "LAYER" "MAKE" "BLT3" "COLOR" "6" "BLT3" "LT" "HIDDEN" "BLT3" "")
(COMMAND "LAYER" "MAKE" "DIM" "COLOR" "3" "DIM" "LT" "CONTINUOUS" "DIM" "")
(COMMAND "LAYER" "MAKE" "DIM1" "COLOR" "3" "DIM1" "LT" "CONTINUOUS" "DIM1" "")
(COMMAND "LAYER" "MAKE" "DIM2" "COLOR" "3" "DIM2" "LT" "CONTINUOUS" "DIM2" "")
(COMMAND "LAYER" "MAKE" "DIM3" "COLOR" "3" "DIM3" "LT" "CONTINUOUS" "DIM3" "")
(COMMAND "LAYER" "MAKE" "MARK" "COLOR" "4" "MARK" "LT" "CONTINUOUS" "MARK" "")
(COMMAND "LAYER" "MAKE" "TEXT" "COLOR" "4" "TEXT" "LT" "CONTINUOUS" "TEXT" "")
(COMMAND "LAYER" "MAKE" "PLOT" "COLOR" "4" "PLOT" "LT" "CONTINUOUS" "PLOT" "")

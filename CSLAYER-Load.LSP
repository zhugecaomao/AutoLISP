(defun c:w     () (command "layer" "s" "wall" ""))
(defun c:wf    () (command "layer" "s" "beam" "off" "wall" ""))
(defun c:b     () (command "layer" "s" "beam" ""))
(defun c:bf    () (command "layer" "s" "wall" "off" "beam" ""))
(defun c:d     () (command "layer" "s" "dim" ""))
(defun c:df    () (command "layer" "s" "wall" "off" "dim" ""))
(defun c:x     () (command "layer" "s" "axis" ""))
(defun c:xf    () (command "layer" "s" "dim" "off" "axis" ""))
(defun c:v     () (command "layer" "s" "temp" ""))
(defun c:vf    () (command "layer" "s" "wall" "off" "temp" ""))
(defun c:g     () (command "layer" "s" "ldm" ""))
(defun c:gf    () (command "layer" "s" "dim" "off" "ldm" ""))
(defun c:zz    () (command "layer" "s" "zz" ""))
(defun c:zf    () (command "layer" "s" "wall" "off" "zz" ""))
(defun c:cf    () (command "layer" "s" "wall" "off" "window" ""))
(defun c:mf    () (command "layer" "s" "wall" "off" "door" ""))
(defun c:ow    () (command "layer" "s" "wall" "off" "zz,ldm,dim,axis,beam,window,door" ""))
(defun c:ob    () (command "layer" "s" "beam" "off" "zz,ldm,dim,axis,wall,window,door" ""))
(defun c:od    () (command "layer" "s" "dim" "off" "zz,ldm,axis,wall,window,door,beam" ""))
(defun c:oz    () (command "layer" "s" "zz" "off" "dim,ldm,axis,wall,window,door,beam" ""))
(defun c:ao    () (command "layer" "on" "zz,dim,ldm,axis,wall,window,door,beam" ""))
(defun c:csla  () (cslayer))
(princ "\n\t Copyright 1996,6,23 ------ 陈松,南昌 ")
(princ "\n\t CSLAYER 扩展图层管理已加载.命令:W-wall/B-beam/D-dim/X-axis/F-temp ")
(princ "\n\t G-ldm/ZZ-zz ")
(princ)

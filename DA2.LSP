(  defun c:da2 ()
;(IF (= (TYPE F1) 'FILE ) "YES"  (STOP))
;(IF (= (TYPE F2) 'FILE ) "YES" (STOP))
       (GRAPHSCR)
    (setq a (entget (car (entsel "\nSelect line:"))))
                   (initget (+ 1 4))
    (setq n (getint "\nInput divid number:"))
                   (initget (+ 1 4))
    (setq l (getreAl "\nInput divid line long:"))
                   (initget 1 )
    (setq p (getpoint "\nSelect divid side:"))
    (setq p1 (CDR (assoc 10 a)))
    (setq p2 (CDR (assoc 11 a)))
    (SETQ DIS (DISTANCE P1 P2 ))
    (setq avl (/ DIS n))
    (setq  x1 (car p1 ))
    (setq   y1 (cadr p1))
    (setq   x2 (car p2))
    (setq  y2 (cadr p2))
    (setq angs (ANGLE p1 p2 ))
    (setq angp (angle p1 p))
    (if (> angs angp )
          (setq ang (- angs (dtr 90)))
          (setq ang (+ angs (dtr 90)))
    )
       (if (= angs 0)
           (progn
             (if ( > ( cadr p) (cadr p1))
                 (setq ang (+ angs (dtr 90)))
                 (setq ang (- angs (dtr 90)))
             )
           )
      )
    (setq ll 0)
    (repeat (+ n 1)
          (setq   z (polar  p1  angs ll ))
          (setq   w (polar  z  ang l ))

          (command "LINE"  z w "")
           (setq ll (+ ll avl))
    )


 )

;*****DRAW A "LEADER"LINE ******
;(IF (= (TYPE F1) 'FILE ) "YES"  (STOP))
;(IF (= (TYPE F2) 'FILE ) "YES" (STOP))
(DEFUN C:DA4 ()
         (GRAPHSCR)
    (COMMAND "ORTHO" "ON" )
    (COMMAND "LAYER" "S" "DIM3" "")
           (INITGET 1)
    (SETQ P1 (GETPOINT "\n START POINT:"))
    (SETQ CAC (GETDIST P1  "\nEND POINT"))
    (SETQ P2 (GRREAD ""))
    (SETQ P  (CDR P2))
    (SETQ P3 (LIST (CAR P1) (CADR (CAR P) ) ) )
    (SETQ ANGTD (ANGLE P1 P3))
    (SETQ TXTD (GETSTRING "\n TEXT>:"))
    (COMMAND "DIM" "LEADER" P1 P3 P3 ""  " " EXIT)
    (SETQ P4 (POLAR P3 ANGTD 2.5))
     (COMMAND "TEXT" "M" P4 "3" "0" TXTD)
)

(DEFUN C:DA7   ( / P1 P2 P3 PP1 PP2 )
;(IF (= (TYPE F1) 'FILE ) "YES"  (STOP))
;(IF (= (TYPE F2) 'FILE ) "YES" (STOP))
              (GRAPHSCR)
;  (COMMAND "SETVAR" "ORTHOMODE" "1")
   (SETQ P1 (GETPOINT"\nSTART POINT:"))
   (SETQ P2 (GETPOINT"\nTO POINT:" P1))
   (SETQ D1 2.75)
   (SETQ L1 1)
   (REPEAT 100
     (COMMAND "LINE" P1 P2 "")
     (SETQ P3 (GETPOINT"\nTO POINT:" P2))
     (SETQ ANG21 (ANGLE  P2 P1))
     (SETQ ANG23 (ANGLE  P2 P3))
     (SETQ ANG12 (ANGLE  P1 P2))
     (SETQ PP1 (POLAR P2 ANG21 D1))
     (SETQ PP2 (POLAR PP1 ANG23 L1))
     (IF (/= ANG12 ANG23)  (PROGN
       (SETQ APP1PP2 (ANGLE PP1 PP2))
       (SETQ APP1P1 (ANGLE  P1 PP1))

       (SETQ DR1 (POLAR PP1  APP1PP2 (* 0.25 -1)))
       (SETQ DR1-1 (POLAR DR1  APP1P1 3.0 ))

       (SETQ DR2 (POLAR PP1  APP1PP2 0.25))
       (SETQ DR2-1 (POLAR DR2  APP1P1 2.5 ))

       (SETQ DR3 (POLAR DR1-1  APP1PP2 3))
       (SETQ DR3-1 (POLAR DR2-1  APP1PP2 2.5))
       (COMMAND "LINE" DR1 DR1-1 DR3 "")
       (COMMAND "LINE" DR2 DR2-1 DR3-1 "")
;      (COMMAND "TEXT" "M"  DR1  "0.1" "0" "DR1")
;      (COMMAND "TEXT" "M"  DR2  "0.1" "0" "DR2")
;      (COMMAND "TEXT" "M"  DR1-1  "0.1" "0" "DR1-1")
;      (COMMAND "TEXT" "M"  DR2-1  "0.1" "0" "DR2-1")
     ))
     (SETQ P1 P2)
     (SETQ P2 P3)
   )
)

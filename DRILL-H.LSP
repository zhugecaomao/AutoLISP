(defun c:drill-h ()
;(IF (= (TYPE F1) 'FILE ) "YES"  (STOP))
;(IF (= (TYPE F2) 'FILE ) "YES" (STOP))

   (setq d (getreal "\n How about the drill diameter ?"))
   (setq l (getdist "\n How longer you want ?"))
 (defun setup()
;   (setq d (getreal "\n How about the drill diameter ?"))
;   (setq l (getdist "\n How longer you want ?"))
   (setq base (getpoint "\n Where will you put on the drill ?"))
   (setq x1 (eval (car base)))
   (setq y1 (eval (cadr base)))

   (setq d1 (/ d 2))
   (setq g (* 0.57735 d1))
   (setq p1 (list (- x1 d1) y1))
   (setq p2 (list (+ x1 d1) y1))
   (setq p3 (list (+ x1 d1) (+ y1 l)))
   (setq p4 (list (- x1 d1) (+ y1 l)))
   (setq p5 (list x1 (+ y1 l g)))
   (command "linetype" "s" "hidden" "" "")
   (command "pline" p1 "w" "0" "0" p2 p3 p4 p1 "")
   (command "pline" p3 "w" "0" "0" p5 p4 "")
   (command "linetype" "s" "continuous" "" "")
   (setup)
 )
   (setup)
 )

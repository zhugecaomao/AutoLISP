(DEFUN C:DRTXT()
  (SETQ TT (GETREAL"\nTXET HIGH"))
  (COMMAND "TEXT" DR1 TT "" "DR1")
  (COMMAND "TEXT" DR2 TT "" "DR2")
  (COMMAND "TEXT" DR3 TT "" "DR3")
  (COMMAND "TEXT" DR4 TT "" "DR4")
  (COMMAND "TEXT" DR5 TT "" "DR5")
  (COMMAND "TEXT" DR6 TT "" "DR6")
  (COMMAND "TEXT" DR7 TT "" "DR7")
  (COMMAND "TEXT" DR8 TT "" "DR8")
  (COMMAND "TEXT" DR9 TT "" "DR9")
  (COMMAND "TEXT" KR1  TT "" "KR1 ")
  (COMMAND "TEXT" KR2  TT "" "KR2 ")
  (COMMAND "TEXT" KR3  TT "" "KR3 ")
  (COMMAND "TEXT" KR4  TT "" "KR4 ")
  (COMMAND "TEXT" CR8  TT "" "CR8 ")
  (COMMAND "TEXT" CR9  TT "" "CR9 ")
  (COMMAND "TEXT" CR1  TT "" "CR1 ")
  (COMMAND "TEXT" CR2  TT "" "CR2 ")
  (COMMAND "TEXT" CR3  TT "" "CR3 ")
  (COMMAND "TEXT" CR4  TT "" "CR4 ")
  (COMMAND "TEXT" CR5  TT "" "CR5 ")
  (COMMAND "TEXT" CR6  TT "" "CR6 ")
  (COMMAND "TEXT" CR7  TT "" "CR7 ")

  (COMMAND "TEXT" DR11 TT "" "DR11")
  (COMMAND "TEXT" DR22 TT "" "DR22")
  (COMMAND "TEXT" DR33 TT "" "DR33")
  (COMMAND "TEXT" DR44 TT "" "DR44")
  (COMMAND "TEXT" DR55 TT "" "DR55")
  (COMMAND "TEXT" DR66 TT "" "DR66")
  (COMMAND "TEXT" DR77 TT "" "DR77")
  (COMMAND "TEXT" DR88 TT "" "DR88")
  (COMMAND "TEXT" DR99 TT "" "DR99")
  (COMMAND "TEXT" KR11  TT "" "KR11 ")
  (COMMAND "TEXT" KR22  TT "" "KR22 ")
  (COMMAND "TEXT" KR33  TT "" "KR33 ")
  (COMMAND "TEXT" KR44  TT "" "KR44 ")
  (COMMAND "TEXT" CR88  TT "" "CR88 ")
  (COMMAND "TEXT" CR99  TT "" "CR99 ")
  (COMMAND "TEXT" CR11  TT "" "CR11 ")
  (COMMAND "TEXT" CR22  TT "" "CR22 ")
  (COMMAND "TEXT" CR33  TT "" "CR33 ")
  (COMMAND "TEXT" CR44  TT "" "CR44 ")
  (COMMAND "TEXT" CR55  TT "" "CR55 ")
  (COMMAND "TEXT" CR66  TT "" "CR66 ")
  (COMMAND "TEXT" CR77  TT "" "CR77 ")

)

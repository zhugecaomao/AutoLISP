Attribute VB_Name = "Module1"
    
    

'数字求和、加、乘、除
Public Sub totalarea()
Dim ssobj As AcadSelectionSet
Dim i As Integer, j As Integer, k As Integer
Dim bztext As String, sum As Double
Dim keywordlist As String, keyvalue As String
Dim lchar As String, mchar As String, rchar As String
Dim x As Double



'清空选择集
    If ThisDrawing.SelectionSets.Count <> 0 Then
        For i = 0 To ThisDrawing.SelectionSets.Count - 1
            Set ssobj = ThisDrawing.SelectionSets.Item(i)
            ssobj.Delete
        Next
    End If


      '创建选择集
    Set ssobj = ThisDrawing.SelectionSets.Add("ss1")
    
    '选择图元
    ssobj.SelectOnScreen
    
    
    
        
    sum = 0
    
    
    If ssobj.Count <> 0 Then
        '等待输入
        keywordlist = "s S a A m M d D"
    
        ThisDrawing.Utility.InitializeUserInput 1, keywordlist
    
        keyvalue = ThisDrawing.Utility.GetKeyword("选择操作：求和（S)/加（A)/乘（M)/除（D）---")
    
        Select Case keyvalue
            Case "A"
            x = ThisDrawing.Utility.GetReal("输入加数：")
            Case "M"
            x = ThisDrawing.Utility.GetReal("输入乘数：")
            Case "D"
            ThisDrawing.Utility.InitializeUserInput 2
            
            x = ThisDrawing.Utility.GetReal("输入除数：")
        End Select
        
            
        
        For i = 0 To ssobj.Count - 1
            
            '若选择的是 acadtext,提取文本
            If ssobj.Item(i).ObjectName = "AcDbText" Then
                
                bztext = Trim(ssobj.Item(i).TextString)
                mchar = bztext
                    lchar = ""
                    While Not IsNumeric(Left$(mchar, 1)) And Len(mchar) > 1
                    
                    lchar = lchar + Left$(mchar, 1)
                    mchar = Mid$(mchar, 2)
                    Wend
                    
                    rchar = ""
                    While Not IsNumeric(Right$(mchar, 1)) And Len(mchar) > 1
                    rchar = Right$(mchar, 1) + rchar
                    mchar = Left$(mchar, Len(mchar) - 1)
                    Wend
                    
                If IsNumeric(mchar) Then
                
                    Select Case keyvalue
    
                    Case "S"
                                
                    sum = sum + Val(mchar)
                    j = j + 1
                    
                    Case "A"
                    mchar = Str$(Val(mchar) + x)
                    bztext = lchar + Trim$(mchar) + rchar
                    ssobj.Item(i).TextString = bztext
                    
                    Case "M"
                    mchar = Str$(x * Val(mchar))
                    bztext = lchar + Trim$(mchar) + rchar
                    ssobj.Item(i).TextString = bztext
                    
                    Case "D"
                    mchar = Str$(Val(mchar) / x)
                    bztext = lchar + Trim$(mchar) + rchar
                    ssobj.Item(i).TextString = bztext
                    End Select
                    
                End If
            
            End If
            
        Next
        
        Select Case keyvalue
        
        Case "S"
        
        ThisDrawing.Utility.Prompt Str$(j) & " numbers have been added" & "   Total is :" & Str$(sum) & "   Average is :" & Str$(sum / j)

        End Select
        
     ssobj.Clear
     End If

   
End Sub

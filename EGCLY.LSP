(DEFUN C:EGCLY()
(SETQ ANS (strcase (GETSTRING "\nDO YOU WANT TO CHANGE LAST SETTING <Y/N> N:")))
(IF (= ANS "Y")
    (PROGN
       (PROMPT "\nPLEASE SETTING LAYER:" )
       (SETQ FC (OPEN "C:/ACAD/ACAD/SUPPORT/EG.SET" "w"))
       (PROMPT "\nE.P CONTINUE OF LAYER " )(PROMPT "<")(PROMPT EGCNT) (PROMPT ">:")
       (setq EGCNT (GETSTRING T))
       (IF (= EGCNT "")
              (WRITE-LINE "0" FC)
              (WRITE-LINE EGCNT FC)
       )
       (PROMPT "\nE.P CENTER OF LAYER " )(PROMPT "<")(PROMPT EGCEN) (PROMPT ">:")
       (setq EGCEN (GETSTRING T))
       (IF (= EGCEN "")
              (WRITE-LINE "CEN" FC)
              (WRITE-LINE EGCEN FC)
       )
       (PROMPT "\nE.P HIDDEN OF LAYER " )(PROMPT "<")(PROMPT EGHID) (PROMPT ">:")
       (setq EGHID (GETSTRING T))
       (IF (= EGHID "")
              (WRITE-LINE "HID" FC)
              (WRITE-LINE EGHID FC)
       )
       (PROMPT "\nE.P THE WORDS " )(PROMPT "<")(PROMPT EGDIM) (PROMPT ">:")
       (setq EGDIM (GETSTRING T))
       (IF (= EGDIM "")
              (WRITE-LINE "EG" FC)
              (WRITE-LINE EGDIM FC)
       )
       (PROMPT "\nE.P TEXT OF LAYER " )(PROMPT "<")(PROMPT EGTXT)(PROMPT ">:")
       (setq EGTXT (GETSTRING T))
       (IF (= EGTXT "")
              (WRITE-LINE "TEXT" FC)
              (WRITE-LINE EGTXT FC)
       )
       (CLOSE FC)
       (SETQ FC (OPEN "C:/ACAD/ACAD/SUPPORT/EG.SET" "r"))
       (SETQ EGCNT (READ-LINE FC))
       (SETQ EGCEN (READ-LINE FC))
       (SETQ EGHID (READ-LINE FC))
       (SETQ EGDIM (READ-LINE FC))
       (SETQ EGTXT (READ-LINE FC))
       (CLOSE FC)
       (PROMPT "\nE.P CONTINUE OF LAYER NOW IS:" )(PROMPT EGCNT)(TERPRI)
       (PROMPT "\nE.P CENTER   OF LAYER NOW IS:" ) (PROMPT EGCEN)(TERPRI)
       (PROMPT "\nE.P HIDDEN   OF LAYER NOW IS:" ) (PROMPT EGHID)(TERPRI)
       (PROMPT "\nE.P DIMENSION OF LAYER IS:" ) (PROMPT EGDIM)(TERPRI)
       (PROMPT "\nE.P TEXT   OF WORD IS:" ) (PROMPT EGTXT)(TERPRI)
  )
)
)

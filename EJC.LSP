(DEFUN EJC()
;(IF (= (TYPE F1) 'FILE ) "YES"  (STOP))
;(IF (= (TYPE F2) 'FILE ) "YES" (STOP))
(NULL P1)
   (REPEAT 100
      (SETQ P1 (GETPOINT"\nInsert Point:"))
      (SETQ D (GETDIST P1"Diameter:"))
      (IF (= D NIL)
          (SETQ D D1)
      )
      (COMMAND "INSERT" "CEN" P1 D D 0)
      (SETQ D1 D)
   )
)

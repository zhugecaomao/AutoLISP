(VMON)
(DEFUN C:ENWORD ()
(SETVAR "CMDECHO" 0)
(SETQ QJ (GETVAR "VIEWCTR"))                                  ;CETER OF PICTURE
(SETQ QM (/ (GETVAR "VIEWSIZE") 2))                           ;HALF HIGH OF PICTURE
(SETQ QQ (- (CADR (GETVAR "VSMAX")) (CADR (GETVAR "VSMIN")))) ;HIGH
(SETQ QN (- (CAR (GETVAR "VSMAX")) (CAR (GETVAR "VSMIN"))))   ;WIDTH
(SETQ QK (/ QQ QN))                                           ;SACLE H/W
(SETQ Q1 (/ QM QK))                                           ;SCALE OF AREA
(SETQ QG (LIST (- (CAR QJ) Q1) (- (CADR QJ) QM)))             ;LEFT RIGHT
(SETQ Q0 (/ (GETVAR "VIEWSIZE") 6) )                          ; 1/6 OF PICTURE
(SETQ QL (/ Q0 1 QK))                                         ;LENGTH OF WIDTH
(SETQ QO (GETPOINT "\nSelect one:"))                          ;SELECT POINT
(SETQ QH (- (CADR QO) (CADR QG)))
(SETQ QC (- (CAR QO) (CAR QG)))
(SETQ QEJ (FIX (/ QC QL)))
(SETQ QJJ (FIX (/ QH Q0)))
(REDRAW)
)
;-------------------------------------------------------------
(DEFUN PPL()
(SETQ PP (STRCAT "C:/ACAD/TE/" PP))
(COMMAND "INSERT" PP PAUSE "" "" PAUSE)
(REDRAW)
)
;-------------------------------------------------------------
(DEFUN C:ENPAGE1 ()
(COMMAND "VSLIDE" "C:/ACAD/HON/SLD/EN1")
(C:CHWORD)
(COND ((AND(= QEJ 0)(= QJJ 5))(SETQ PP "EN11")(PPL))
((AND(= QEJ 0)(= QJJ 4))(SETQ PP "EN12")(PPL))
((AND(= QEJ 0)(= QJJ 3))(SETQ PP "EN13")(PPL))
((AND(= QEJ 0)(= QJJ 2))(SETQ PP "EN14")(PPL))
((AND(= QEJ 0)(= QJJ 1))(SETQ PP "EN15")(PPL))
((AND(= QEJ 0)(= QJJ 0))(SETQ PP "EN16")(PPL))
((AND(= QEJ 1)(= QJJ 5))(SETQ PP "EN17")(PPL))
((AND(= QEJ 1)(= QJJ 4))(SETQ PP "EN18")(PPL))
((AND(= QEJ 1)(= QJJ 3))(SETQ PP "EN21")(PPL))
((AND(= QEJ 1)(= QJJ 2))(SETQ PP "EN22")(PPL))
((AND(= QEJ 1)(= QJJ 1))(SETQ PP "EN23")(PPL))
((AND(= QEJ 1)(= QJJ 0))(SETQ PP "EN24")(PPL))
((AND(= QEJ 2)(= QJJ 5))(SETQ PP "EN25")(PPL))
((AND(= QEJ 2)(= QJJ 4))(SETQ PP "EN26")(PPL))
((AND(= QEJ 2)(= QJJ 3))(SETQ PP "EN27")(PPL))
((AND(= QEJ 2)(= QJJ 2))(SETQ PP "EN28")(PPL))
((AND(= QEJ 2)(= QJJ 1))(SETQ PP "EN31")(PPL))
((AND(= QEJ 2)(= QJJ 0))(SETQ PP "EN32")(PPL))
((AND(= QEJ 3)(= QJJ 5))(SETQ PP "EN33")(PPL))
((AND(= QEJ 3)(= QJJ 4))(SETQ PP "EN34"))
((AND(= QEJ 3)(= QJJ 3))(SETQ PP "EN35"))
((AND(= QEJ 3)(= QJJ 2))(SETQ PP "EN36"))
((AND(= QEJ 3)(= QJJ 1))(SETQ PP "EN37"))
((AND(= QEJ 3)(= QJJ 0))(SETQ PP "EN38"))
((AND(= QEJ 4)(= QJJ 5))(SETQ PP "EN41"))
((AND(= QEJ 4)(= QJJ 4))(SETQ PP "EN42"))
((AND(= QEJ 4)(= QJJ 3))(SETQ PP "EN43"))
((AND(= QEJ 4)(= QJJ 2))(SETQ PP "EN44"))
((AND(= QEJ 4)(= QJJ 1))(SETQ PP "EN45"))
((AND(= QEJ 4)(= QJJ 0))(SETQ PP "EN46"))
((AND(= QEJ 5)(= QJJ 5))(SETQ PP "EN47"))
((AND(= QEJ 5)(= QJJ 4))(SETQ PP "EN48"))
((AND(= QEJ 5)(= QJJ 3))(SETQ PP "EN51"))
((AND(= QEJ 5)(= QJJ 2))(SETQ PP "EN52"))
((AND(= QEJ 5)(= QJJ 1))(C:ENPAGE2))
((AND(= QEJ 5)(= QJJ 0))(COMMAND "CANCLE"))
)
(SETVAR "CMDECHO" 1)
)
;-------------------------------------------------------------
(DEFUN C:ENPAGE2 ()
(COMMAND "VSLIDE" "C:/ACAD/HON/SLD/EN2")
(C:CHWORD)
(COND ((AND(= QEJ 0)(= QJJ 5))(SETQ PP "CH56")(PPL))
((AND(= QEJ 0)(= QJJ 4))(SETQ PP "EN53")(PPL))
((AND(= QEJ 0)(= QJJ 3))(SETQ PP "EN54")(PPL))
((AND(= QEJ 0)(= QJJ 2))(SETQ PP "EN55")(PPL))
((AND(= QEJ 0)(= QJJ 1))(SETQ PP "EN56")(PPL))
((AND(= QEJ 0)(= QJJ 0))(SETQ PP "EN57")(PPL))
((AND(= QEJ 1)(= QJJ 5))(SETQ PP "EN58")(PPL))
((AND(= QEJ 1)(= QJJ 4))(SETQ PP "EN61")(PPL))
((AND(= QEJ 1)(= QJJ 3))(SETQ PP "EN62")(PPL))
((AND(= QEJ 1)(= QJJ 2))(SETQ PP "EN63")(PPL))
((AND(= QEJ 1)(= QJJ 1))(SETQ PP "EN64")(PPL))
((AND(= QEJ 1)(= QJJ 0))(SETQ PP "EN65")(PPL))
((AND(= QEJ 2)(= QJJ 5))(SETQ PP "EN66")(PPL))
((AND(= QEJ 2)(= QJJ 4))(SETQ PP "EN67")(PPL))
((AND(= QEJ 2)(= QJJ 3))(SETQ PP "EN68")(PPL))
((AND(= QEJ 2)(= QJJ 2))(SETQ PP "EN71")(PPL))
((AND(= QEJ 2)(= QJJ 1))(SETQ PP "EN72")(PPL))
((AND(= QEJ 2)(= QJJ 0))(SETQ PP "EN73")(PPL))
((AND(= QEJ 3)(= QJJ 5))(SETQ PP "EN74")(PPL))
((AND(= QEJ 3)(= QJJ 4))(SETQ PP "EN75")(PPL))
((AND(= QEJ 3)(= QJJ 3))(SETQ PP "EN76")(PPL))
((AND(= QEJ 3)(= QJJ 2))(SETQ PP "EN77")(PPL))
((AND(= QEJ 3)(= QJJ 1))(SETQ PP "EN78")(PPL))
((AND(= QEJ 3)(= QJJ 0)))
((AND(= QEJ 4)(= QJJ 5)))
((AND(= QEJ 4)(= QJJ 4)))
((AND(= QEJ 4)(= QJJ 3)))
((AND(= QEJ 4)(= QJJ 2)))
((AND(= QEJ 4)(= QJJ 1)))
((AND(= QEJ 4)(= QJJ 0)))
((AND(= QEJ 5)(= QJJ 5)))
((AND(= QEJ 5)(= QJJ 4)))
((AND(= QEJ 5)(= QJJ 3)))
((AND(= QEJ 5)(= QJJ 2)))
((AND(= QEJ 5)(= QJJ 1))(C:PAGE1))
((AND(= QEJ 5)(= QJJ 0))(COMMAND "CANCLE"))
)
(SETVAR "CMDECHO" 1)
)

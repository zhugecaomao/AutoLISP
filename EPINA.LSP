(defun c:epina()
(setq F (getvar "blipmode")) (setvar "blipmode" 0)
(setq p (getpoint "\n Insert point:"))
(setq D (getreal "\n Enter epina diameter [0.1-20]:"))
(setq L (getreal "\n Enter epina length:"))
(setq A (getreal "\n Enter epina angle:"))
(setq B (* pi (/ A 180.0)))
(if (and (> D 0) (<= D 1.5))
 (progn (setq D1 3.0) (setq H 4.0) (setq D2 4.0)))
(if (and (> D 1.5) (<= D 2.5))
 (progn (setq D1 5.0) (setq H 4.0) (setq D2 6.0)))
(if (and (> D 2.5) (<= D 3.0))
 (progn (setq D1 6.0) (setq H 4.0) (setq D2 7.0)))
(if (and (> D 3.0) (<= D 3.5))
 (progn (setq D1 7.0) (setq H 4.0) (setq D2 8.0)))
(if (and (> D 3.5) (<= D 4.0))
 (progn (setq D1 8.0) (setq H 6.0) (setq D2 9.0)))
(if (and (> D 4.0) (<= D 5.0))
 (progn (setq D1 9.0) (setq H 6.0) (setq D2 10.0)))
(if (and (> D 5.0) (<= D 6.0))
 (progn (setq D1 10.0) (setq H 6.0) (setq D2 11.0)))
(if (and (> D 6.0) (<= D 7.0))
 (progn (setq D1 11.0) (setq H 6.0) (setq D2 12.0)))
(if (and (> D 7.0) (<= D 8.0))
 (progn (setq D1 13.0) (setq H 8.0) (setq D2 14.0)))
(if (and (> D 8.0) (<= D 10.0))
 (progn (setq D1 15.0) (setq H 8.0) (setq D2 16.0)))
(if (and (> D 10.0) (<= D 12.0))
 (progn (setq D1 17.0) (setq H 8.0) (SETQ D2 18.0)))
(if (and (> D 12.0) (<= D 14.0))
 (progn (setq D1 19.0) (setq H 8.0) (setq D2 20.0)))
(if (and (> D 14.0) (<= D 16.0))
 (progn (setq D1 21.0) (setq H 8.0) (setq D2 22.0)))
(if (and (> D 16.0) (<= D 18.0))
 (progn (setq D1 23.0) (setq H 8.0) (setq D2 24.0)))
(if (and (> D 18.0) (<= D 20.0))
 (progn (setq D1 25.0) (setq H 8.0) (setq D2 26.0)))
(setq p1 (polar p B H))
(setq p2 (polar p B L))
(setq p3 (polar p1 (+ B (/ pi 2)) (* 0.5 D)))
(setq p4 (polar p1 (- B (/ pi 2)) (* 0.5 D)))
(setq p5 (polar p1 (+ B (/ pi 2)) (* 0.5 D1)))
(setq p6 (polar p1 (- B (/ pi 2)) (* 0.5 D1)))
(setq p7 (polar p1 (+ B (/ pi 2)) (* 0.5 D2)))
(setq p8 (polar p1 (- B (/ pi 2)) (* 0.5 D2)))
(setq p9 (polar p (+ B (/ pi 2)) (* 0.5 D2)))
(setq p10 (polar p (- B (/ pi 2)) (* 0.5 D2)))
(setq p11 (polar p (+ B (/ pi 2)) (* 0.5 D1)))
(setq p12 (polar p (- B (/ pi 2)) (* 0.5 D1)))
(setq p13 (polar p2 (+ B (/ pi 2)) (* 0.5 D)))
(setq p14 (polar p2 (- B (/ pi 2)) (* 0.5 D)))
(command "line" p9 p7 p8 p10 "")
(command "line" p11 p5 "")
(command "line" p12 p6 "")
(command "line" p3 p13 p14 p4 "")
(setvar "blipmode" F))

DEFUN C:CIRDIM
;(IF (= (TYPE F1) 'FILE ) "YES"  (STOP))
;(IF (= (TYPE F2) 'FILE ) "YES" (STOP))
(PROMPT "\nSelect object:")
(COMMAND "SETVAR" "HIGHLIGHT" "1")
(COMMAND "SELECT" "AU" "\\")
(SETQ EXP (GETPOINT"\nEXTEND POINT:"))
(SETQ SA (SSGET "P" ))
(SETQ N (SSLENGTH SA))
(SETQ I 0)
(REPEAT N
  (SETQ NA (ENTGET (SSNAME SA I)))
  (SETQ I (+ 1 I))
  (SETQ NB (ASSOC 0 NA))
  (IF (= "LINE" (CDR NB))
      (PROGN
          (SETQ SP1 (ASSOC 10 NA))
          (SETQ SP2 (ASSOC 11 NA))
          (SETQ NP1 (CDR SP1))
          (SETQ NP2 (CDR SP2))
          (SETQ AG1 (ANGLE NP1 NP2))
          (SETQ AG2 (* PI 0.5))
          (SETQ DR3 (POLAR EXP (+ AG1 AG2) 3))
          (SETQ DR4 (POLAR EXP (- AG1 AG2) 3))
          (SETQ INT (INTERS NP1 NP2 DR3 DR4 NIL))
          (COMMAND "CHANGE" "P" "" INT)
       )
 )
)

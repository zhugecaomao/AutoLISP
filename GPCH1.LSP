DEFUN C:GRCH1
;SET LAYER
(COMMAND "SETVAR" "CMDECHO" 0)
(SETQ NY (GETVAR "CLAYER"))
;(IF (= (TYPE F1) 'FILE ) "YES"  (STOP))
;(IF (= (TYPE F2) 'FILE ) "YES" (STOP))
(setq G1SET (findfile "/acad/HON/SET/G1.SET"))
(IF (= G1SET NIL)
    (PROGN
       (PROMPT "\nPLEASE SETTING LAYER IN GROUP 1:" )
       (SETQ FC (OPEN "/acad/HON/SET/G1.SET" "w"))
       (SETQ G1NUM (GETINT"\nHOW MANY LAYERS DO YOU WANT IN GROUP 1:"))
       (WRITE-LINE (ITOA G1NUM) FC)
       (SETQ ORDER 0)
       (REPEAT G1NUM
          (SETQ ORDER (+ ORDER 1))
          (SETQ ORDER1 (STRCAT (ITOA ORDER) "TH"))
          (PROMPT"\nKEYIN LAYER NAME:<")(PROMPT ORDER1)(PROMPT">")
          (SETQ G1LAY (GETSTRING T))
          (IF (= G1LAY "")
              (WRITE-LINE "" FC)
              (WRITE-LINE G1LAY FC)
          )
       )
       (CLOSE FC)
    )
)

 (IF (/= G1SET NIL)
     (PROGN
        (SETQ FC (OPEN "/acad/HON/SET/G1.SET" "r"))
        (SETQ G1NUM (READ-LINE FC))
        (IF (OR (= G1NUM "") (= G1NUM NIL))
            (PROGN
               (CLOSE FC)
               (COMMAND "G1")
            )
        )
        (IF (/= G1NUM NIL)
           (PROGN
              (SETQ G1NUM (ATOI G1NUM))
              (SETQ FY1 "")
              (SETQ FY "")
              (REPEAT G1NUM
                 (SETQ G1LAY (READ-LINE FC))
                 (SETQ FY (STRCAT G1LAY "," FY))
                 (SETQ FY1 FY)
                 (PROMPT "\n" )(PROMPT G1LAY)
                 (IF (= G1LAY "")
                     (PROGN
                       (COMMAND "G1")
                       (SETQ G1NUM 0)
                     )
                 )
              )
           )
        )
     )
 )

 (COMMAND "LAYER" "FREEZE" FY "")







  ;     (SETQ FC (OPEN "/acad/HON/SET/GRP1.SET" "r"))
  ;     (SETQ #GP1NUM (GETINT"\nHOW MANY LAYERS DO YOU WANT IN GROUP 1:"))
  ;     (SETQ #GP1NUM (READ-LINE FC))
  ;     (SETQ #GP1NUM (ATOI #GP1NUM))
  ;     (PRIN1 #GP1NUM)
  ;     (PROMPT "LAYER IN GROUP1:" )
  ;     (REPEAT #GP1NUM
  ;         (setq #GRP1 (GETSTRING T"\nKEYIN LAYER NAME:"))
  ;         (SETQ #GRP1 (STRCAT "#GRP" (ITOA #GP1NUM)))
  ;         (PROMPT #GRP1)
  ;         (IF (= #GRP1 "")
  ;             (WRITE-LINE "" FC)
  ;             (WRITE-LINE #GRP1 FC)
  ;         )
  ;     )
  ;     (CLOSE FC)
  ;  )
  ;



;       (PROMPT "\nG.P CONTINUE OF LAYER IS:" )(PROMPT GPCNT)(TERPRI)
;       (PROMPT "\nG.P CENTER OF LAYER IS:" ) (PROMPT GPCEN)(TERPRI)
;       (PROMPT "\nG.P HIDDEN OF LAYER IS:" ) (PROMPT GPHID)(TERPRI)
;       (PROMPT "\nG.P DIMENSION OF LAYER IS:" ) (PROMPT GPDIM)(TERPRI)
;       (PROMPT "\nG.P TEXT   OF LAYER IS:" ) (PROMPT GPTXT)(TERPRI)
;    )
;)
;
;(SETQ ANS (strcase (GETSTRING "\nDO YOU WANT TO CHANGE LAST SETTING <Y/N> N:")))
;(IF (= ANS "Y")
;    (PROGN
;       (PROMPT "\nPLEASE SETTING LAYER:" )
;       (SETQ FC (OPEN "/acad/HON/SET/GRP1.SET" "w"))
;       (PROMPT "\nG.P CONTINUE OF LAYER " )(PROMPT "<")(PROMPT GPCNT) (PROMPT ">:")
;       (setq GPCNT (GETSTRING T))
;       (IF (= GPCNT "")
;              (WRITE-LINE "0" FC)
;              (WRITE-LINE GPCNT FC)
;       )
;       (PROMPT "\nG.P CENTER OF LAYER " )(PROMPT "<")(PROMPT GPCEN) (PROMPT ">:")
;       (setq GPCEN (GETSTRING T))
;       (IF (= GPCEN "")
;              (WRITE-LINE "CEN" FC)
;              (WRITE-LINE GPCEN FC)
;       )
;       (PROMPT "\nG.P HIDDEN OF LAYER " )(PROMPT "<")(PROMPT GPHID) (PROMPT ">:")
;       (setq GPHID (GETSTRING T))
;       (IF (= GPHID "")
;              (WRITE-LINE "HID" FC)
;              (WRITE-LINE GPHID FC)
;       )
;       (PROMPT "\nG.P THE WORDS " )(PROMPT "<")(PROMPT GPDIM) (PROMPT ">:")
;       (setq GPDIM (GETSTRING T))
;       (IF (= GPDIM "")
;              (WRITE-LINE "GP" FC)
;              (WRITE-LINE GPDIM FC)
;       )
;       (PROMPT "\nG.P TEXT OF LAYER " )(PROMPT "<")(PROMPT GPTXT)(PROMPT ">:")
;       (setq GPTXT (GETSTRING T))
;       (IF (= GPTXT "")
;              (WRITE-LINE "TEXT" FC)
;              (WRITE-LINE GPTXT FC)
;       )
;       (CLOSE FC)
;       (SETQ FC (OPEN "/acad/HON/SET/GRP1.SET" "r"))
;       (SETQ GPCNT (READ-LINE FC))
;       (SETQ GPCEN (READ-LINE FC))
;       (SETQ GPHID (READ-LINE FC))
;       (SETQ GPDIM (READ-LINE FC))
;       (SETQ GPTXT (READ-LINE FC))
;       (CLOSE FC)
;       (PROMPT "\nG.P CONTINUE OF LAYER NOW IS:" )(PROMPT GPCNT)(TERPRI)
;       (PROMPT "\nG.P CENTER   OF LAYER NOW IS:" ) (PROMPT GPCEN)(TERPRI)
;       (PROMPT "\nG.P HIDDEN   OF LAYER NOW IS:" ) (PROMPT GPHID)(TERPRI)
;       (PROMPT "\nG.P DIMENSION OF LAYER IS:" ) (PROMPT GPDIM)(TERPRI)
;       (PROMPT "\nG.P TEXT   OF WORD IS:" ) (PROMPT GPTXT)(TERPRI)
;  )
;)
;)
;

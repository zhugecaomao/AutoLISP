DEFUN C:GROUP2
;SET LAYER
(COMMAND "SETVAR" "CMDECHO" 0)
(SETQ NY (GETVAR "CLAYER"))
;(IF (= (TYPE F1) 'FILE ) "YES"  (STOP))
;(IF (= (TYPE F2) 'FILE ) "YES" (STOP))
(setq G2SET (findfile "C:/ACAD/ACAD/SUPPORT/G2.SET"))
(IF (= G2SET NIL)
    (PROGN
       (PROMPT "\nPLEASE SETTING LAYER IN GROUP 2:" )
       (SETQ FC (OPEN "C:/ACAD/ACAD/SUPPORT/G2.SET" "w"))
       (SETQ G2NUM (GETINT"\nHOW MANY LAYERS DO YOU WANT IN GROUP 2:"))
       (WRITE-LINE (ITOA G2NUM) FC)
       (SETQ ORDER 0)
       (REPEAT G2NUM
          (SETQ ORDER (+ ORDER 1))
          (SETQ ORDER2 (STRCAT (ITOA ORDER) "TH"))
          (PROMPT"\nKEYIN LAYER NAME:<")(PROMPT ORDER2)(PROMPT">")
          (SETQ G2LAY (GETSTRING T))
          (IF (= G2LAY "")
              (WRITE-LINE "" FC)
              (WRITE-LINE G2LAY FC)
          )
       )
       (CLOSE FC)
    )
)

 (IF (/= G2SET NIL)
     (PROGN
        (SETQ FC (OPEN "C:/ACAD/ACAD/SUPPORT/G2.SET" "r"))
        (SETQ G2NUM (READ-LINE FC))
        (IF (OR (= G2NUM "") (= G2NUM NIL))
            (PROGN
               (CLOSE FC)
               (COMMAND "G2")
            )
        )
        (IF (/= G2NUM NIL)
           (PROGN
              (SETQ G2NUM (ATOI G2NUM))
              (SETQ FY2 "")
              (SETQ FY "")
              (REPEAT G2NUM
                 (SETQ G2LAY (READ-LINE FC))
                 (SETQ FY (STRCAT G2LAY "," FY))
                 (SETQ FY2 FY)
                 (PROMPT "\n" )(PROMPT G2LAY)
                 (IF (= G2LAY "")
                     (PROGN
                       (COMMAND "G2")
                       (SETQ G2NUM 0)
                     )
                 )
              )
           )
        )
     )
 )

DEFUN C:GRSET1
;SET LAYER
(COMMAND "SETVAR" "CMDECHO" 0)
(SETQ NY (GETVAR "CLAYER"))
;(IF (= (TYPE F1) 'FILE ) "YES"  (STOP))
;(IF (= (TYPE F2) 'FILE ) "YES" (STOP))
(setq G1SET (findfile "/ACAD/HON/SET/G1.SET"))
(IF (= G1SET NIL)
    (PROGN
       (PROMPT "\nPLEASE SETTING LAYER IN GROUP 1:" )
       (SETQ FC (OPEN "/ACAD/HON/SET/G1.SET" "w"))
       (SETQ G1NUM (GETINT"\nHOW MANY LAYERS DO YOU WANT IN GROUP 1:"))
       (WRITE-LINE (ITOA G1NUM) FC)
       (SETQ ORDER 0)
       (REPEAT G1NUM
          (SETQ ORDER (+ ORDER 1))
          (SETQ ORDER1 (STRCAT (ITOA ORDER) "TH"))
          (PROMPT"\nKEYIN LAYER NAME:<")(PROMPT ORDER1)(PROMPT">")
          (SETQ G1LAY (GETSTRING T))
          (IF (= G1LAY "")
              (WRITE-LINE "" FC)
              (WRITE-LINE G1LAY FC)
          )
       )
       (CLOSE FC)
    )
)

 (IF (/= G1SET NIL)
     (PROGN
        (SETQ FC (OPEN "/ACAD/HON/SET/G1.SET" "r"))
        (SETQ G1NUM (READ-LINE FC))
;       (SETQ G1LAY (READ-LINE FC))
        (IF (OR (= G1NUM "") (= G1NUM NIL))
            (PROGN
               (CLOSE FC)
               (COMMAND G1)
            )
        )
       (IF (OR (= G1NUM NIL) (= G1NUM NIL))
         (PROGN
           (PROMPT "\nPLEASE SETTING LAYER IN GROUP 1:" )
           (SETQ FC (OPEN "/ACAD/HON/SET/G1.SET" "w"))
           (SETQ G1NUM (GETINT"\nHOW MANY LAYERS DO YOU WANT IN GROUP 1:"))
           (WRITE-LINE (ITOA G1NUM) FC)
           (SETQ ORDER 0)
           (REPEAT G1NUM
              (SETQ ORDER (+ ORDER 1))
              (SETQ ORDER1 (STRCAT (ITOA ORDER) "TH"))
              (PROMPT"\nKEYIN LAYER NAME:<")(PROMPT ORDER1)(PROMPT">")
              (SETQ G1LAY (GETSTRING T))
              (IF (= G1LAY "")
                  (WRITE-LINE "" FC)
                  (WRITE-LINE G1LAY FC)
              )
           )
           (CLOSE FC)
         )
       )
        (IF (/= G1NUM NIL)
           (PROGN
              (SETQ FC (OPEN "/ACAD/HON/SET/G1.SET" "r"))
              (SETQ G1NUM (READ-LINE FC))
              (PROMPT"\nGROUP 1 LAYERS HAVE:")
              (PROMPT "<" )
              (SETQ G1NUM (ATOI G1NUM))
              (SETQ FY1 "")
              (SETQ FY "")
              (REPEAT G1NUM
                 (SETQ G1LAY (READ-LINE FC))
                 (SETQ FY (STRCAT G1LAY "," FY))
                 (SETQ FY1 FY)
                 (PROMPT G1LAY)(PROMPT"  ")
                 (IF (= G1LAY "")
                     (PROGN
                       (COMMAND "G1")
                       (SETQ G1NUM 0)
                     )
                 )
              )
              (PROMPT">")
           (CLOSE FC)
           )
        )
     )
 )

;(COMMAND "LAYER" "FREEZE" FY "")

(SETQ ANS (strcase (GETSTRING "\nDO YOU WANT TO CHANGE LAST SETTING <Y/N> N:")))
 (IF (= ANS "Y")
     (PROGN
       (PROMPT "\nPLEASE SETTING LAYER IN GROUP 1:" )
       (SETQ FC (OPEN "/ACAD/HON/SET/G1.SET" "w"))
       (PROMPT"\nHOW MANY LAYERS DO YOU WANT IN GROUP 1:")
       (PROMPT"<")(PRIN1 G1NUM)(PROMPT">")
       (SETQ G1NUMN G1NUM)
       (SETQ G1NUM (GETINT))
       (IF (OR (= G1NUM "") (= G1NUM NIL))
           (WRITE-LINE (ITOA G1NUMN) FC)
           (WRITE-LINE (ITOA G1NUM) FC)
       )
       (SETQ ORDER 0)
       (IF (OR (= G1NUM "") (= G1NUM NIL))
           (SETQ G1NUM G1NUMN)
       )
       (REPEAT G1NUM
          (SETQ ORDER (+ ORDER 1))
          (SETQ ORDER1 (STRCAT (ITOA ORDER) "TH"))
          (PROMPT"\nKEYIN LAYER NAME:<")(PROMPT ORDER1)(PROMPT">")
          (SETQ G1LAY (GETSTRING T))
          (IF (= G1LAY "")
              (WRITE-LINE "" FC)
              (WRITE-LINE G1LAY FC)
          )
       )
       (CLOSE FC)
     )
 )

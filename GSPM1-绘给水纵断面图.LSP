(Defun tk ()
 (prompt "\n\t\t现在输入图框特征")
 (prompt "\n\t**************************************************************")
 (setvar "CMDECHO" 0)
 (setq n (length a))
 (setq i 0 llb nil hhb nil)
 (while (< i n)
  (setq llb (cons (car (cadr (nth i a))) llb))
  (setq hhb (cons (cadr (cadr (nth i a))) hhb))
  (setq i (+ i 1))
 )
 (setq maxh (apply 'max hhb))
 (setq maxl (apply '+ llb))
 (setq maxh (+ (cadr pd0)  40.0 (- maxh (cadr (cadr (car a))))))
 (setq maxl (+ (car pd0) (* k (+ maxl 20.0))))
 (prompt (strcat "\n_____你的图形高为" (rtos maxh 2 0) "_____"))
 (setq kd (getdist "\n 请输入图框宽;/297/420/594/841/: "))
 (cond ((= kd 297) (setq dd "/420/631/841/1051/1261/1472/")))
 (cond ((= kd 420) (setq dd "/594/743/841/892/1041/1189/1338/")))
 (cond ((= kd 594) (setq dd "/841/1051/1261/1472/")))
 (cond ((= kd 841) (setq dd "/1189/1338/1487/")))
 (prompt (strcat "\n_____你的图形长为" (rtos maxl 2 0) "_____"))
 (setq cd (getdist (strcat "\n 请输入图框长;" dd ": ")))
 (command "limits" '(0.0 0.0) (list cd kd))
 (command "zoom" "a")
 (command "grid" 10.0 )
 (command "layer" "new" "tk" "" )
 (command "line" '(0.0 0.0) (list cd 0.0) (list cd kd) (list 0.0
                  kd) "c" )
 (command "pline" '(25.0 10.0) "w" "0.9" "" (list (- cd 10.0) 10.0)
                    (list (- cd 10.0) (- kd 10.0)) (list 25.0 (- kd
                    10.0)) "c" )
 (command "insert" "c:/jiangdh/tl/tq" (list (- cd 10.0) 10.0) "0.01"
          "0.01" "")
 (command "insert" "c:/jiangdh/tl/hq" (list 25.0 (- kd 10.0)) ""
          "" "")
)

(defun nk ()
 (setq dc (+ 10.0 (car (last (dm2)))))
 (command "color" "3")
 (command "pline" '(75.0 65.0) "w" "0.3" "" (list dc 65.0)
                  (list dc 195.0) '(75.0 195.0) "c")
 (command "pline" '(75.0 75.0 ) (list dc 75.0) "")
 (command "pline" '(75.0 85.0 ) (list dc 85.0) "")
 (command "pline" '(75.0 100.0) (list dc 100.0) "")
 (command "pline" '(75.0 115.0 ) (list dc 115.0) "")
 (command "pline" '(75.0 122.5) (list dc 122.5) "")
 (command "pline" '(75.0 130.0 ) (list dc 130.0) "")
 (command "pline" '(75.0 145.0 ) (list dc 145.0) "")
 (command "pline" '(75.0 160.0) (list dc 160.0) "")
 (command "pline" '(75.0 175.0) (list dc 175.0) "")
 (command "pline" '(125.0 65.0) '(125.0 195.0) "")
 (command "text" "c" '(100.0 67.5) "5" "0" "阀门井尺寸(毫米)")
 (command "text" "c" '(100.0 77.5) "5" "" "节 点 编 号")
 (command "text" "c" '(100.0 90.0) "5" "" "接入管尺寸(毫米)")
 (command "text" "c" '(100.0 105.0) "5" "" "平 面 距 离(米)")
 (command "text" "c" '(100.0 116.25) "5" "" "坡 度   ")
 (command "insert" "c:/jiangdh/tl/qfh" '(104.0 115.0) "" "" "")
 (command "text" "c" '(100.0 123.75) "5" "" "管径(毫米) 管材")
 (command "text" "c" '(100.0 135.0) "5" "" "埋  深 (米)") 
 (command "text" "c" '(100.0 150.0) "5" "" "设计管中心标高(米)")
 (command "text" "c" '(100.0 165.0) "5" "" "设计地面标高(米)")
 (command "text" "c" '(100.0 182.5) "5" "" "道路里程(桩号)(米)")
)

;***************************** DMX ********************************
(defun dm1 ( )
 (prompt   "\n\t\t 现在请输入地面控制点")
 (prompt "\n\t*****************************************************")
 (setq n (getint "\n 地面控制点数: "))
 (prompt "\n -----*-----*-----")
 (setq i 1)
 (setq bg1 (getdist "\n 起点标高: "))
 (setq b1 nil)
 (while (< i n)
  (setq p1 (getpoint (strcat " \n < " (itoa (+ i 1)) " >点(距离,标高): ")))
  (setq b1 (cons (list (+ i 1) p1) b1))
  (setq i (+ i 1))
 )
 (cons (list 1 (list 0.00 bg1)) (reverse b1))
)

(defun chx1 ( b )
 (prompt   "\n\t\t 现在请校对和修改")
 (prompt "\n\t*****************************************************")
 (setq n (length b))
 (setq i 0)
 (while (< i n)
  (setq jp1 (ntH i b))
  (setq jp nil)
  (setq p1 (getpoint (strcat " \n <"(itoa (car jp1))
   " > 点新值 < "
   (rtos (car (cadr jp1)) 2 3) "," (rtos (cadr (cadr jp1)) 2 3)
  " >: ")))
  (IF (NULL P1) (SETQ P1 (CADR JP1)) (SETQ JP T))
  (if  JP         (setq b (subst (list (CAR JP1) P1) JP1 B)))
  (setq i (+ i 1))
 )
 b
)

(defun prt1 ( a )
 (setq n (length a))
 (princ "\n") (princ "控制点") (princ "\t\t") (princ "水平距离")
    (princ "\t\t") (princ "地面标高")
 (setq i 0)
 (while (< i n)
  (princ "\n") (princ (car (nth i a))) (princ "\t\t")
   (princ (rtos (car (cadr (nth i a))) 2 3)) (princ "\t\t\t")
   (princ (rtos (cadr (cadr (nth i a))) 2 3))
  (setq i (+ i 1))
 )
)

(defun dm2 ( )
 (setq n (length a))
 (setq i 0)
 (setq minh (apply 'min (mapcar 'cadr (mapcar 'cadr a))))
 (setq pt0 pd0)
 (setq m (car pt0))
 (setq b1 nil)
 (setq b2 nil)
 (while (< i n)
  (setq p1 (cadr (nth i a)))
  (setq b1 (cons (+ m (* k (car p1))) b1))
  (setq b2 (cons (+ (* 10.0 (- (cadr p1) minh)) (cadr pt0)) b2))
  (setq m (+ m (* k (car p1))))
  (setq i (+ i 1))
 )
 (reverse (mapcar 'list b1 b2 ))
)
;***************************** SSGX ********************************
(defun sg1 ( )
 (prompt  "\n\t\t 现在请输入管道节点特征")
 (prompt "\n\***************************************************************")
 (setq n (getint "\n 节点数: "))
 (prompt "\n -----*-----*-----")
;; (setq j1 (strcase (getstring t "\n 起始节点编号: ")))

 (setq j1 (getstring t "\n 起始节点编号: "))
 (setq ll (strlen j1))
 (setq aa (strcase (substr j1 1 1)))
 (setq bb (substr j1 2 (1- ll)))
 (setq j1 (strcat aa bb)) 

 (while (= j1 "")
;;  (setq j1 (getstring t "\n不许空输入! 重输: ")))

   (setq j1 (getstring t "\n不许空输入! 重输: "))
   (setq ll (strlen j1))
   (setq aa (strcase (substr j1 1 1)))
   (setq bb (substr j1 2 (1- ll)))
   (setq j1 (strcat aa bb))
 )


 (initget 1)
 (setq lch0 (getstring t "\n 起始节点里程<桩号><米>: "))
 (initget 1)
 (setq gs0 (getdist "\n 管道起点埋深<米>: "))
 (setq jtd0 "")
 (setq aa (getstring t "\n 起始节点特性<1.接入管 2.阀门井 3.一般节点 4.排气阀 5.排泥阀>: "))
 (setq f "t")
 (cond ((= aa "1")
         (while f
           (setq jtd2 (getstring t "\n 接入管类型<1.东 2.西 3.南 4.北 5.退出>:"))
               (cond ((= jtd2 "1") (setq jtd2 "东"))
                     ((= jtd2 "2") (setq jtd2 "西"))
                     ((= jtd2 "3") (setq jtd2 "南"))
                     ((= jtd2 "4") (setq jtd2 "北"))
                     ((= jtd2 "5") (setq f nil) (setq jtd2 ""))
               )
           (if (/= jtd2 "")
            (progn 
              (setq jtd1 (strcase (getstring t "\n 接入管直径<DNxx>")))  
              (setq jtd0 (strcat jtd2 jtd1 jtd0) )
            )
           )
         )
       )
       ((= aa "2")
         (setq jtd0 "阀门井")
       )
       ((= aa "3")
         (setq jtd0 "一般节点")
       )
       ((= aa "4")
         (setq jtd0 "排气阀")
       )
       ((= aa "5")
         (setq jtd0 "排泥阀")
       )
 )

 (setq i 2)
 (setq jb nil jlb nil lchb nil gsb nil jtdb nil)
 (while (<= i n)
  (prompt "\n -----*-----*-----")
;;  (setq j (getstring t (strcat " \n < "(itoa i)" >节点编号: ")))

  (setq j (getstring t (strcat " \n < "(itoa i)" >节点编号: ")))
  (setq ll (strlen j))
  (setq aa (strcase (substr j 1 1)))
  (setq bb (substr j 2 (1- ll)))
  (setq j (strcat aa bb))

  (while (= j "")
;;   (setq j (getstring t "\n不许空输入! 重输: ")))

   (setq j (getstring t "\n不许空输入! 重输: "))
   (setq ll (strlen j))
   (setq aa (strcase (substr j 1 1)))
   (setq bb (substr j 2 (1- ll)))
   (setq j (strcat aa bb))

  )
  (initget 1)
  (setq jl (getdist "\n 距前节点水平距离: "))
  (initget 1)
  (setq lch (getstring t "\n 该节点里程<桩号><米>: "))
  (initget 1)
  (setq gs (getdist "\n 该节点管道埋深: "))

  (setq jtdx "")
  (setq aa (getstring t "\n 该节点特性<1.接入管 2.阀门井 3.一般节点 4.排气阀 5.排泥阀>: "))
  (setq f "t")
  (cond ((= aa "1")
         (while f
          (setq jtd2 (getstring t "\n 接入管类型<1.东 2.西 3.南 4.北 5.退出>:"))
               (cond ((= jtd2 "1") (setq jtd2 "东"))
                     ((= jtd2 "2") (setq jtd2 "西"))
                     ((= jtd2 "3") (setq jtd2 "南"))
                     ((= jtd2 "4") (setq jtd2 "北"))
                     ((= jtd2 "5") (setq f nil) (setq jtd2 ""))
               )

           (if (/= jtd2 "")
             (progn 
              (setq jtd1 (strcase (getstring t "\n 接入管直径<DNxx>")))  
              (setq jtdx (strcat jtd2 jtd1 jtdx))
             )
           )
         )
       )
       ((= aa "2")
         (setq jtdx "阀门井")
       )
       ((= aa "3")
         (setq jtdx "一般节点")
       )
       ((= aa "4")
         (setq jtdx "排气阀")
       )
       ((= aa "5")
         (setq jtdx "排泥阀")
       )
  )

;;  (setq spzj (getorient "\n 该节点水平转角<180>: "))
;;  (if (= spzj nil) (setq spzj pi))
  (setq jb (cons j jb))
  (setq jlb (cons jl jlb))
  (setq lchb (cons lch lchb))
  (setq gsb (cons gs gsb))
  (setq jtdb (cons jtdx jtdb)) 
;;  (setq spzjb (cons spzj spzjb))
  (setq i (+ i 1))
 )
 (setq jb (reverse jb) jlb (reverse jlb) lchb (reverse lchb)  
       gsb (reverse gsb) jtdb (reverse jtdb))
)

(defun chx2 ( )
 (prompt   "\n\t\t 现在请校对和修改")
 (prompt "\n\t*****************************************************")
 (setq j0 j1 lch1 lch0 gs1 gs0 jtd1 jtd0)
;; (setq j1 (strcase (getstring t (strcat
;;                   "\n 起始节点编号< " j0 " >: "))))

 (setq j1 (getstring t (strcat "\n 起始节点编号< " j0 " >: ")))
 (if (= j1 "") (setq j1 j0))
 (setq ll (strlen j1))
 (setq aa (strcase (substr j1 1 1)))
 (setq bb (substr j1 2 (1- ll)))
 (setq j1 (strcat aa bb))


;; (if (= j1 "") (setq j1 j0))
 (setq lch0 (getstring (strcat "\n 起始节点里程<桩号><米>< "
                                       lch1 " >: ")))
 (if (= lch0 "") (setq lch0 lch1))

 (setq gs0 (getdist (strcat "\n 管道起点埋深< "
                                       (rtos gs1 2 2) " >: ")))
 (if (= gs0 nil) (setq gs0 gs1))

 (setq jtd0 "")
 (setq aa (getstring t (strcat 
  "\n 起始节点特性 <"jtd1"> <1.接入管 2.阀门井 3.一般节点 4.排气阀 5.排泥阀>: ")))
 (setq f "t")
 (cond ((= aa "") (setq jtd0 jtd1))
       ((= aa "1")
         (while f
           (setq jtd2 (getstring t "\n 接入管类型<1.东 2.西 3.南 4.北 5.退出>:"))
               (cond ((= jtd2 "1") (setq jtd2 "东"))
                     ((= jtd2 "2") (setq jtd2 "西"))
                     ((= jtd2 "3") (setq jtd2 "南"))
                     ((= jtd2 "4") (setq jtd2 "北"))
                     ((= jtd2 "5") (setq f nil) (setq jtd2 ""))
               )
           (if (/= jtd2 "")
            (progn
              (setq jtd1 (strcase (getstring t "\n 接入管直径<DNxx>:")))  
              (setq jtd0 (strcat jtd2 jtd1 jtd0))
            )
           )
         )
       )
       ((= aa "2")
         (setq jtd0 "阀门井")
       )
       ((= aa "3")
         (setq jtd0 "一般节点")
       )
       ((= aa "4")
         (setq jtd0 "排气阀")
       )
       ((= aa "5")
         (setq jtd0 "排泥阀")
       )
  )

 (setq n (length jlb))
 (setq bj jb bjl jlb chbl lchb bgs gsb jtdb1 jtdb)
 (setq jb nil jlb nil lchb nil gsb nil jtdb nil)
 (setq i 0)
 (while (< i n)
  (prompt " -----*-----*-----")
;;  (setq j (getstring t (strcat "\n < "   (itoa (+ i 2))
;;    " >节点编号< " (nth i bj) " >: ")))

  (setq j (getstring t (strcat "\n < "   (itoa (+ i 2))
    " >节点编号< " (nth i bj) " >: ")))
  (if (= j "") (setq j (nth i bj)))
  (setq ll (strlen j))
  (setq aa (strcase (substr j 1 1)))
  (setq bb (substr j 2 (1- ll)))
  (setq j (strcat aa bb))


;;  (if (= j "") (setq j (nth i bj)))
  (setq jl (getdist (strcat "\n 距前节点水平距离 < " (rtos
          (nth i bjl) 2 2) " >: ")))
  (if (= jl nil) (setq jl (nth i bjl)))
  (setq lch (getstring t (strcat "\n 该节点里程<桩号><米>< "
                       (nth i chbl) " >: ")))
  (if (= lch "") (setq lch (nth i chbl)))

  (setq gs (getdist (strcat "\n 该节点管道埋深< "
                       (rtos (nth i bgs) 2 3)   " >: ")))
  (if (= gs nil) (setq gs (nth i bgs)))

  (setq jtdx "")
  (setq aa (getstring t 
  (strcat "\n 该节点特性<"(nth i jtdb1)"> <1.接入管 2.阀门井 3.一般节点 4.排气阀 5.排泥阀>: ")))
  (setq f "t")
  (cond ((= aa "") (setq jtdx (nth i jtdb1))) 
        ((= aa "1")
         (while f
           (setq jtd2 (getstring t "\n 接入管类型<1.东 2.西 3.南 4.北 5.退出>:"))
               (cond ((= jtd2 "1") (setq jtd2 "东"))
                     ((= jtd2 "2") (setq jtd2 "西"))
                     ((= jtd2 "3") (setq jtd2 "南"))
                     ((= jtd2 "4") (setq jtd2 "北"))
                     ((= jtd2 "5") (setq f nil) (setq jtd2 ""))
               )
           (if (/= jtd2 "")
            (progn
               (setq jtd1 (strcase (getstring t "\n 接入管直径<DNxx>")))  
               (setq jtdx (strcat jtd2 jtd1 jtdx))
            )
           )
         )
       )
       ((= aa "2")
         (setq jtdx "阀门井")
       )
       ((= aa "3")
         (setq jtdx "一般节点")
       )
       ((= aa "4")
         (setq jtdx "排气阀")
       )
       ((= aa "5")
         (setq jtdx "排泥阀")
       )
  )
  (setq jtdb (cons jtdx jtdb))

;;  (if (<= (nth i bspzj) pi) (setq ang (angtos (nth i bspzj) 0 2))
;;     (setq ang (rtos (* -1.0 (atof (angtos (- (* 2.0 pi) (nth i
;;               bspzj)) 0 2))) 2 2)))
;;  (setq spzj (getorient (strcat "\n 该节点水平转角< " ang
;;                                                    " >: ")))
;; (if (= spzj nil) (setq spzj (nth i bspzj)))
  (setq jb (cons j jb))
  (setq jlb (cons jl jlb))
  (setq lchb (cons lch lchb))
  (setq gsb (cons gs gsb))
;;  (setq spzjb (cons spzj spzjb))
  (setq i (+ i 1))
 )
 (setq jb (reverse jb) jlb (reverse jlb) lchb (reverse lchb)
       gsb (reverse gsb) jtdb (reverse jtdb))
 (setq z (cons (list j1 (list 0.0 lch0 gs0 jtd0)) (mapcar 'list jb (mapcar
                        'list jlb lchb gsb jtdb))))
)

(defun prt2 ( )
 (princ "\n") (princ "节点")  (princ "\t") (princ "水平距离")
 (princ "      ") (princ "节点里程<桩号>") (princ "   ") (princ "管道埋深") 
 (princ "\t      ") (princ "节点特征")
 (princ "\n") (princ j1) (princ "\t")   (princ "0.00")
 (princ "\t\t") (princ lch0) (princ "            ") (princ (rtos gs0 2 2)) 
 (princ "\t      ") (princ jtd0)
 (setq n (length jb))
 (setq i 0)
 (while (< i n)
  (princ "\n") (princ (nth i jb)) (princ "\t")   (princ (rtos (nth
  i jlb) 2 2)) (princ "\t\t") (princ (nth i lchb)) 
  (princ "            ") (princ (rtos (nth i gsb) 2 2))
  (princ "\t      ") (princ (nth i jtdb))
;; (if (<= (nth i spzjb) pi)
;; (princ (angtos (nth I spzjb) 0 2)) 
;; (princ (rtos (* -1.0 (atof (angtos (- (* 2.0 pi) (nth i spzjb)) 0 2))) 2 2)))
  (setq i (+ i 1))
 )
)

(defun sg2 ()
 (setq f z)
 (setq n (length f))
 (setq b3 (mapcar 'car f))
 (setq i 0)
 (setq m (car pt0))
 (setq b1 nil)
 (setq b2 (mapcar 'caddr (mapcar 'cadr f)))
 (while (< i n)
  (setq p1 (cadr (nth i f)))
  (setq b1 (cons (+ m (* k (car p1))) b1))
  (setq m (+ m (* k (car p1))))
  (setq i (+ i 1))
 )
 (setq b1 (reverse b1))
 (reverse (mapcar 'list b3 (mapcar 'list b1 b2)))
)

(defun sg3 ( g h )
 (setq gg (mapcar 'car (mapcar 'cadr (reverse g))))
 (setq hh (mapcar 'car h))
 (setq hh (reverse (cons cd (reverse hh))))
 (setq hg (reverse (cons (list cd 0.0) (reverse h))))
 (setq maxh (+ 30.0 (apply 'max (mapcar 'cadr h))))
 (setq n (length gg))
 (setq i 0)
 (setq jd nil)
 (setq dmbg nil)
 (setq gdms nil)
 (while (< i n)
  (setq l1 (nth i gg))
  (setq gs (* 10.0 (cadr (cadr (nth i (reverse g))))))
  (setq gdms (cons gs gdms))
  (setq i1 0)
  (setq d "t")
  (while d
   (setq l2 (nth i1 hh))
   (if (> l2 l1) (setq d nil))
   (setq i1 (+ i1 1))
  )
  (setq m (- (length hh) (length (member l2 hh))))
  (setq p1 (list l1 120.0))
  (setq p2 (list l1 (+ maxh 10.0)))
  (setq p3 (nth (- m 1) hg))
  (setq p4 (nth m hg))
  (if (inters p1 p2 p3 p4 nil) (setq pt p3))
  (if (inters p1 p2 p3 p4 t  ) (setq pt (inters p1 p2 p3 p4)))
  (setq jd (cons pt jd))
  (setq dmbg (cons (+ (* 0.1 (- (cadr pt) (cadr pt0))) minh) dmbg))
  (setq i (+ i 1))
 )
 (setq jd (reverse jd) gdms (reverse gdms))
 (setq dmbg (reverse dmbg))
 (setq gdbg (mapcar '- dmbg (mapcar 'cadr (mapcar 'cadr (reverse g
             )))))

 (setq gj (nth 2 (nth 0 gjgc)))
 (cond ((= gj "DN100") 
        (setq gj 1.0) (setq gj001 "%%C1000") (setq pq001 "%%C1200")
       )
       ((= gj "DN150") 
        (setq gj 1.5) (setq gj001 "%%C1200") (setq pq001 "%%C1200")
       )
       ((= gj "DN200") 
        (setq gj 2.0) (setq gj001 "%%C1400") (setq pq001 "%%C1200")
        (setq ng001 75.0 nfj001 "%%C1200" shj001 "%%C700")
       )
       ((= gj "DN250") 
        (setq gj 2.5) (setq gj001 "%%C1400") (setq pq001 "%%C1200")
        (setq ng001 75.0 nfj001 "%%C1200" shj001 "%%C700")      
       )
       ((= gj "DN300") 
        (setq gj 3.0) (setq gj001 "%%C1600") (setq pq001 "%%C1200")
        (setq ng001 75.0 nfj001 "%%C1200" shj001 "%%C700")      
       )
       ((= gj "DN350") 
        (setq gj 3.5) (setq gj001 "%%C1800") (setq pq001 "%%C1200")
        (setq ng001 75.0 nfj001 "%%C1200" shj001 "%%C700")      
       )
       ((= gj "DN400") 
        (setq gj 4.0) (setq gj001 "%%C1800") (setq pq001 "%%C1200")
        (setq ng001 100.0 nfj001 "%%C1200" shj001 "%%C1000")      
       )
       ((= gj "DN450") 
        (setq gj 4.5) (setq gj001 "%%C2000") (setq pq001 "%%C1200")
        (setq ng001 150.0 nfj001 "%%C1200" shj001 "%%C1000")      
       )
       ((= gj "DN500") 
        (setq gj 5.0) (setq gj001 "%%C2000") (setq pq001 "%%C1200")
        (setq ng001 150.0 nfj001 "%%C1200" shj001 "%%C1000")      
       )
       ((= gj "DN600") 
        (setq gj 6.0) (setq gj001 "%%C2200") (setq pq001 "%%C1200")
        (setq ng001 150.0 nfj001 "%%C1200" shj001 "%%C1000")      
       )
       ((= gj "DN700") 
        (setq gj 7.0) (setq gj001 "%%C2400") (setq pq001 "%%C1400")
        (setq ng001 200.0 nfj001 "%%C1400" shj001 "%%C1000")      
       )
       ((= gj "DN800") 
        (setq gj 8.0) (setq gj001 "%%C2400") (setq pq001 "%%C1400")
        (setq ng001 200.0 nfj001 "%%C1400" shj001 "%%C1000")      
       )
       ((= gj "DN900") 
        (setq gj 9.0) (setq gj001 "%%C2800") (setq pq001 "%%C1400")
        (setq ng001 250.0 nfj001 "%%C1400" shj001 "%%C1200")      
       )
       ((= gj "DN1000") 
        (setq gj 10.0) (setq gj001 "%%C2800") (setq pq001 "%%C1400")
        (setq ng001 300.0 nfj001 "%%C1600" shj001 "%%C1200")      
       )
       ((= gj "DN1100") 
        (setq gj 11.0) (setq gj001 "%%C2800") (setq pq001 "%%C1400")
        (setq ng001 300.0 nfj001 "%%C1600" shj001 "%%C1200")      
       )
 )
 (setq gdms1 nil gdms2 nil)
 (setq n1 (length gdms))
 (setq nn 0)
 (while (< nn n1)
   (setq gdms1 (cons (+ (nth nn gdms) (/ gj 2.0)) gdms1))
   (setq nn (+ nn 1))
 )
 (setq gdms1 (reverse gdms1))
 (setq nn 0)
 (while (< nn n1)
   (setq gdms2 (cons (- (nth nn gdms) (/ gj 2.0)) gdms2)) 
   (setq nn (+ nn 1))
 )
 (setq gdms2 (reverse gdms2))

 (setq gdzb1 (mapcar 'list (mapcar 'car (reverse g)) (mapcar 'list
            gg (mapcar '- (mapcar 'cadr jd) gdms1))))
 (setq gdzb2 (mapcar 'list (mapcar 'car (reverse g)) (mapcar 'list
            gg (mapcar '- (mapcar 'cadr jd) gdms2))))
 (setq gdzb (mapcar 'list (mapcar 'car (reverse g)) (mapcar 'list
            gg (mapcar '- (mapcar 'cadr jd) gdms))))

                                                 
)


;**************************** GJGC *******************************
(defun gjgc1 ( )
 (prompt "\n\t\t现在请输入管径,管材")
 (prompt "\n\t**************************************************************")
 (prompt "\n\t\t键入<E or e>退出输入")
;; (setq j1 (strcase (getstring t "\n 起始节点编号: ")))

 (setq j1 (getstring t "\n 起始节点编号: "))
 (setq ll (strlen j1))
 (setq aa (strcase (substr j1 1 1)))
 (setq bb (substr j1 2 (1- ll)))
 (setq j1 (strcat aa bb))


 (setq gjgc nil)
 (setq d "t")
 (while d
   (while ( = (assoc j1 z) nil)
;;   (setq j1 (strcase (getstring t "\n 没有此节点! 重试: ")))

   (setq j1 (getstring t "\n 没有此节点! 重试: "))
   (setq ll (strlen j1))
   (setq aa (strcase (substr j1 1 1)))
   (setq bb (substr j1 2 (1- ll)))
   (setq j1 (strcat aa bb))


   )

;;  (setq j2 (strcase (getstring t "\n 到节点编号: ")))

   (setq j2 (getstring t "\n 到节点编号: "))
   (setq ll (strlen j2))
   (setq aa (strcase (substr j2 1 1)))
   (setq bb (substr j2 2 (1- ll)))
   (setq j2 (strcat aa bb))

   (while ( = (assoc j2 z) nil)
;;   (setq j2 (strcase (getstring t "\n 没有此节点! 重试: "))))

   (setq j2 (getstring t "\n 没有此节点! 重试: "))
   (setq ll (strlen j2))
   (setq aa (strcase (substr j2 1 1)))
   (setq bb (substr j2 2 (1- ll)))
   (setq j2 (strcat aa bb))

   )

  (setq gj (strcase (getstring t " \n 管径: ")))
  (initget 1 "S I C")
  (setq gc (getkword "\n 管道类型:钢管S/给水球墨铸铁管I/钢筋混凝土管C: "))
  (setq gjgc (cons (list j1 j2 gj (strcase gc)) gjgc))
  (prompt "\n -----*-----*-----")
;;  (setq j1 (strcase (getstring t "\n 起点编号<下段管道>: ")))

  (setq j1 (getstring t "\n 起点编号<下段管道>: "))
  (setq ll (strlen j1))
  (setq aa (strcase (substr j1 1 1)))
  (setq bb (substr j1 2 (1- ll)))
  (setq j1 (strcat aa bb))


  (if (or (= j1 "e") (= j1 "E")) (setq d nil))
 )
 (setq gjgc (reverse gjgc))
)

;***************************** GDJC *****************************
(defun gdjc1 ( )
 (prompt "\n\t\t现在请输入管道基础")
 (prompt "\n\t*****************************************************")
 (prompt "\n\t\t键入:<E or e>退出输入")
 (setq j1 (strcase (getstring t " \n 起始节点编号: ")))
 (setq gdjc nil)
 (setq d "t")
 (while d
  (while (= (assoc j1 z) nil)
  (setq j1 (strcase (getstring t "\n 没有此节点! 重试: "))))
  (setq j2 (strcase (getstring t " \n 到节点编号: ")))
  (while (= (assoc j2 z) nil)
  (setq j2 (strcase (getstring t "\n 没有此节点! 重输: "))))
  (initget 1 "SO S SA SVC W")
  (setq jc (getkword "\n 管道基础:素土SO/砂土S/砂桩SA/混凝土桩SVC/木桩W: "))
  (setq gdjc (cons (list j1 j2 (strcase jc)) gdjc))
  (prompt "\n -----*-----*-----")
  (setq j1 (strcase (getstring t " \n 起点编号<下段管道>: ")))
  (if (or (= j1 "e") (= j1 "E")) (setq d nil))
 )
 (setq gdjc (reverse gdjc))
)


;*************************** JCGD ***************************
(defun jcgd1 ( )
 (prompt "\n\t\t\现在请输入过路管道")
 (prompt "\n\t*************************************************************")
 (prompt "\n\t\t键入:<E or e>退出输入")
;; (setq j (strcase (getstring t " \n 距离过路管道最近的前一节点编号: ")))

 (setq j (getstring t " \n 距离过路管道最近的前一节点编号: "))
 (setq ll (strlen j))
 (setq aa (strcase (substr j 1 1)))
 (setq bb (substr j 2 (1- ll)))
 (setq j (strcat aa bb))

 (setq jcgd nil)
 (setq d "t")
 (while d
  (while (= (assoc j z) nil)
;;  (setq j (strcase (getstring t " \n 没有此节点! 重试: "))))

  (setq j (getstring t " \n 没有此节点! 重试: "))
  (setq ll (strlen j))
  (setq aa (strcase (substr j 1 1)))
  (setq bb (substr j 2 (1- ll)))
  (setq j (strcat aa bb))
  
  )


  (initget 3)
  (setq jl (getdist " \n 过路管道到该节点水平距离<米>: "))
  (initget 1 "GS XH YS WS DL TX RQ")
  (setq nx (getkword
  "\n 管道类型:给水GS/循环XH/雨水YS/污水WS/动力DL/通信TX/燃气RQ: "))
  (setq nx (strcase nx))
  (cond ((= nx "GS" )(setq gj (getstring t " \n 管径<DN...>: "))
         (initget 1)
         (setq bg (getdist " \n 管中心标高<米>: ")))

        ((= nx "XH" )(setq gj (getstring t " \n 管径<DN...>: "))
         (initget 1)
         (setq bg (getdist " \n 管中心标高<米>: ")))

        ((= nx "YS" )(setq gj (getstring t " \n 管径<DN...>: "))
         (initget 1)
         (setq bg (getdist " \n 管内底标高<米>: ")))

        ((= nx "WS" )(setq gj (getstring t " \n 管径<DN...>: "))
         (initget 1)
         (setq bg (getdist " \n 管内底标高<米>: ")))

        ((= nx "DL" )(setq gj (getstring t " \n 管径<DN...>: "))
         (initget 1)
         (setq bg (getdist " \n 管外底标高<米>: ")))

        ((= nx "TX")(setq gj (getstring t  "\n 管径<DN...>: "))
         (initget 1)
         (setq bg (getdist " \n 管外底标高<米>: ")))

        ((= nx "RQ" )(setq gj (getstring t  "\n 管径<DN...>: "))
         (initget 1)
         (setq bg (getdist  "\n 管外底标高<米>: ")))
  )

  (initget 1)
  (setq glch (getstring t "\n 请输入该过路管里程<桩号><米>: "))

  (setq jcgd (cons (list j jl nx (strcase gj) bg glch) jcgd))
  (prompt "\n -----*-----*-----")
;;  (setq j (strcase (getstring t " \n 下一根过路管所距离的节点编号: ")))

  (setq j (getstring t " \n 下一根过路管所距离的节点编号: "))
  (setq ll (strlen j))
  (setq aa (strcase (substr j 1 1)))
  (setq bb (substr j 2 (1- ll)))
  (setq j (strcat aa bb))

  (if (or (= j "e") (= j "E")) (setq d nil))
 )
 (setq jcgd (reverse jcgd))
)


;****************************** DRAW ****************************
(defun hdmx ( )
 (command "color" "3")
 (apply 'command (cons "line" (reverse (cons "" (reverse (dm2)
                 )))))
)

(defun hsgx ( )
 (command "color" "1")
 (apply 'command (cons "pline" (cons (cadr (nth 0 gdzb1)) (cons "w"
         (cons "0.9" (cons "" (reverse (cons "" (reverse (cdr
         (mapcar 'cadr gdzb1)))))))))))
 (apply 'command (cons "pline" (cons (cadr (nth 0 gdzb2)) (cons "w"
         (cons "0.9" (cons "" (reverse (cons "" (reverse (cdr
         (mapcar 'cadr gdzb2)))))))))))
 (command "color" "6")
 (command "linetype" "load" "DASHDOT" "" "")
 (apply 'command (cons "pline" (cons (cadr (nth 0 gdzb)) (cons "w"
         (cons "0.0" (cons "" (reverse (cons "" (reverse (cdr
         (mapcar 'cadr gdzb)))))))))))
 (command "change" "l" "" "p" "lt" "DASHDOT" "")
 (command "Ltscale" "3.0")

 (command "color" "1")


;; (command "pline" (list (car (nth 0 jd)) 99.0) (list (car (last
;;                    jd)) 99.0) "")
)

(defun dtr ( a )
   (* pi ( / a 180.0))
)

(defun hcx ( )
 (setq n (length gdzb))
 (setq i 0)
 (while (< i n)
  (setq p1 (nth i jd))
  (if (or (= i 0) (= i (- n 1))) 
      (progn
        (setq p2 (list (car p1) 65.0))
        (command "color" "2")
        (command "line" p1 p2 "")
      )
      (progn
        (setq p3 (list (car p1) 130.0))
        (setq p4 (list (car p1) 122.5))
        (setq p2 (list (car p1) 100.0))
        (command "color" "2")
        (command "line" p1 p3 "")
        (command "line" p4 p2 "")
      )
  )
  (setq i (+ i 1))
 )
 (setq i 0)
 (while (< i n)
  (setq p3 (nth i jd))
  (command "color" "1" )
  (if (< (* k (car (cadr (nth i z)))) 4.0) (setq px (+ (car p3) 4.0)
             ) (setq px (- (car p3) 1.0))) (setq py (- px 3.0))
  (if (< (* k (car (cadr (nth i z)))) 4.0)
    (command "text" (list py 78.0) "2.5" "0" (car (nth i gdzb)))
    (if (= i (1- n))
      (command "text" "r" (list px 78.0) "2.5" "0" (car (nth i gdzb)))
      (command "text" "c" (list px 78.0) "2.5" "0" (car (nth i gdzb)))
    )
  )
   (command "text" (list px 163.5) "2.5" "90" (rtos (nth i dmbg) 2 2))
   (command "text" (list px 179.0) "2.5" "90" (nth i lchb)) 
   (command "text" (list px 134.5) "2.5" "90" (rtos (nth i gsb) 2 2)) 
   (command "text" (list px 147.5) "2.5" "90" (rtos (nth i gdbg) 2 2))
   (if (/= (car (cadr (nth i z))) 0.0)
    (command "text" "c" (list (- (car p3) (* 0.5 (car (cadr (nth i z)
          )) k)) 106.0) "2.5" "0" (rtos (car (cadr (nth i z))) 2 2))
  )
  (setq i (+ i 1))
 )
 (setq i 1)
 (while (< i n)
  (if (= (nth i jlb) 0.0) (setq gf "ww2") (setq gf "ww1"))
  (cond ((= gf "ww1")
        (setq bg1 (nth (- i 1) gdbg) bg2 (nth i gdbg))
        (setq jl (nth i jlb))
        (setq pj (* (/ (- bg2 bg1) jl) 1000.0))
        (setq p3 (nth (- i 1) jd))

        (if (> pj 0.0)
            (progn
              (setq pt01 (list (car p3) 115.0))
              (setq pt02 (list (+ (car p3) (* jl k)) 122.5))
;;              (command "line" pt01 pt02 "")
;;              (command "text" "c" 
              (setq pnt01 (list (+ (car p3) (* 0.418 jl k)) 118.75))
;;                 "2.5" "0" (rtos (abs pj) 2 2)))
            )
        )

       (if (= (rtos pj 2 2) "0.00")
            (progn
              (setq pt01 (list (car p3) 118.75))
              (setq pt02 (list (+ (car p3) (* jl k)) 118.75))
;;              (command "line" pt01 pt02 "")
;;              (command "text" "c" 
              (setq pnt01 (list (+ (car p3) (* 0.5 jl k)) 118.75))
;;                 "2.5" "0" (rtos (abs pj) 2 2)))
            )
        )

        (if (< pj 0.0)
            (progn
              (setq pt01 (list (car p3) 122.5))
              (setq pt02 (list (+ (car p3) (* jl k)) 115.0))
;;              (command "line" pt01 pt02 "")
;;              (command "text" "c" 
              (setq pnt01 (list (+ (car p3) (* 0.618 jl k)) 118.75))
            )
        )
        (command "line" pt01 pt02 "")
;;        (command "text" "c" (list (+ (car p3) (* 0.618 jl k)) 118.75)
;;                 "2.5" "0" (rtos (abs pj) 2 2)))
        (command "text" "c" pnt01
                 "2.5" "0" (rtos (abs pj) 2 2)))


  )
  (setq i (+ i 1))
 )
)

(defun hgjgc ( )
 (setq n (length gjgc))
 (setq i 0)
 (while (< i n)
  (setq pp (nth i gjgc))
  (setq j1 (nth 0 pp) j2 (nth 1 pp) gj (nth 2 pp) gc (nth 3 pp))
  (cond ((= gc "S" ) (setq gc "钢管"))
        ((= gc "I" ) (setq gc "给水球墨铸铁管"))
        ((= gc "C" ) (setq gc "钢筋混凝土管"))
  )
  (setq p1 (list (* 0.5 (+ (car (cadr (assoc j2 gdzb))) (car (
           cadr (assoc j1 gdzb))))) 124.25))
  (command "color" "1")
  (command "text" "r" (list (- (car p1) 4.0) (cadr p1)) "3.5" "0"
           (strcase gj)) 
  (command "text" p1 "5" "0" gc)
  (command "color" "2")
  (command "line" (list (car (cadr (assoc j2 gdzb))) 122.5)
                  (list (car (cadr (assoc j2 gdzb))) 130.0) "")
  (setq i (+ i 1))
 )
)

(defun hjdtz ()
  (setq n (length jtdb))
  (setq i 0)
  (while (< i n)
      (setq xy01 (cadr (nth i gdzb)))
      (setq xy02 (cadr (nth i gdzb2)))
      (setq xy03 (cadr (nth i gdzb1)))    
      (setq xy04 (nth i h))
      (setq xx011 (nth i jtdb))
      (setq tzh (substr xx011 3 2))
      (if (= tzh "DN")
         (progn
           (setq xll (strlen xx011))
           (if (< xll 10)
             (progn
              (setq xx02 "")
              (setq xx01 xx011)
              (setq ddl0 (atof (substr xx011 5 (- xll 4))))
              (setq ddl1 (rtos (/ ddl0 100.0) 2 2))
             )
             (progn
               (setq xx01 (substr xx011 1 (/ xll 2)))
               (setq xx02 (substr xx011 (+ (/ xll 2) 1) (/ xll 2)))
               (setq ddl0 (atof (substr xx011 5 (- (/ xll 2) 4))))
               (setq ddl1 (rtos (/ ddl0 100.0) 2 2))
             )
           )
           (command "color" "4")
           (setq kk01 (list (car xy01) (+ (cadr xy01) (/ ddl0 200.0))))
           (setq kk02 (list (+ (car xy01) (* (/ ddl0 200.0) 0.7)) (cadr xy01)))
           (command "ellipse" "c" xy01 kk01 kk02)
           (command "color" "6")
           ;(command "pedit" "l" "w" "0.3" "x")        
           (setq ppt01 (list (car xy01) 100.00))
           (setq ppt02 (list (car xy01) 85.00))
           (command "line" ppt01 ppt02 "")
           (command "text" "c" (list (- (car xy01) 1.0) 92.5) "2.5" 
                    "90" xx01)
           (command "text" "c" (list (+ (car xy01) 3.5) 92.5) "2.5"
                    "90" xx02)
         )
      )

      (cond ((= xx011 "阀门井")
;;             (command "insert" "c:/jiangdh/tl/fmj001" xy01 "" "" "")
             (setq pt001 (list (- (car xy01) 2.25) (- (cadr xy03) 2.0)))
             (setq pt002 (list (+ (car xy01) 2.25) (- (cadr xy03) 2.0)))
             (setq pt003 (list (+ (car xy01) 2.25) (cadr xy04)))
             (setq pt004 (list (- (car xy01) 2.25) (cadr xy04)))
             (setq kk01 (list (- (car pt001) 1.5) (cadr pt001))) 
             (setq kk02 (list (+ (car pt002) 1.5) (cadr pt002)))
             (setq mm01 (list (- (car xy02) 1.2) (+ (cadr xy02) 1.25)))
             (setq mm02 (list (+ (car xy02) 1.2) (+ (cadr xy02) 1.25)))
             (setq mm03 (list (- (car xy03) 1.2) (- (cadr xy03) 1.25)))
             (setq mm04 (list (+ (car xy03) 1.2) (- (cadr xy03) 1.25)))
             (setq mm05 (list (car xy01) (+ (cadr xy02) 1.2)))
             (setq mm06 (list (car xy01) (- (cadr xy03) 1.2)))
             (command "color" "6")
             (command "pline" pt001 "w" "0.3" "" pt002
                       pt003 pt004 "c")
             (command "pline" kk01 "w" "0.8" "" kk02 "")
             (command "pline" mm01 "w" "0.3" "" mm04 mm02 mm03 "c")
             (command "pline" mm05 "w" "0.3" "" mm06 "")
             (cond ((= i 0)
                (command "text" (list (car xy01) 68.75) "2.5" "0" gj001)
                   )
                   ((= i (1- n))
                (command "text" "r" (list (car xy01) 68.75) "2.5" "0" gj001)
                   )
                   ((and (/= i 0) (/= i (1- n)))
                (command "text" "c" (list (car xy01) 68.75) "2.5" "0" gj001)
                   )
             )
            )

            ((= xx011 "排气阀")
             (command "insert" "c:/jiangdh/tl/pqf001" xy02 "" "" "")
             (setq pt001 (list (- (car xy01) 2.25) (- (cadr xy03) 2.0)))
             (setq pt002 (list (+ (car xy01) 2.25) (- (cadr xy03) 2.0)))
             (setq pt003 (list (+ (car xy01) 2.25) (cadr xy04)))
             (setq pt004 (list (- (car xy01) 2.25) (cadr xy04)))
             (setq kk01 (list (- (car pt001) 2.25) (cadr pt001))) 
             (setq kk02 (list (+ (car pt002) 2.25) (cadr pt002)))
             (command "color" "6")
             (command "pline" pt001 "w" "0.3" "" pt002
                       pt003 pt004 "c")
             (command "pline" kk01 "w" "0.8" "" kk02 "")
             (cond ((= i 0)
                (command "text" (list (car xy01) 68.75) "2.5" "0" pq001)
                   )
                   ((= i (1- n))
                (command "text" "r" (list (car xy01) 68.75) "2.5" "0" pq001)
                   )
                   ((and (/= i 0) (/= i (1- n)))
                (command "text" "c" (list (car xy01) 68.75) "2.5" "0" pq001)
                   )
             )
            )

            ((= xx011 "排泥阀")
             (command "color" "4")
             (setq pn001 (list (car xy03) (+ (cadr xy03) 0.5)))
             (setq pn002 (list (car xy03) 
                               (+ (+ (cadr xy03) (/ ng001 100.0)) 0.5))) 
             (command "ellipse" pn001 pn002 pn002)
             (command "color" "6")
             ;(command "pedit" "l" "w" "0.3" "x")
             (cond ((= i 0)
               (command "text" (list (car xy01) 70.75) "3.0" "0" 
                      (strcat "排泥阀门井" nfj001))
               (command "text" (list (car xy01) 65.75) "3.0" "0" 
                      (strcat "湿井" shj001))
                   )
                   ((= i (1- n))
               (command "text" "r" (list (car xy01) 70.75) "3.0" "0" 
                      (strcat "排泥阀门井" nfj001))
               (command "text" "r" (list (car xy01) 65.75) "3.0" "0" 
                      (strcat "湿井" shj001))
                   )
                   ((and (/= i 0) (/= i (1- n)))
               (command "text" "c" (list (car xy01) 70.75) "3.0" "0" 
                      (strcat "排泥阀门井" nfj001))
               (command "text" "c" (list (car xy01) 65.75) "3.0" "0" 
                      (strcat "湿井" shj001))
                   )
             )

            )
      )
      (setq i (1+ i))
  )
)

(defun hgdjc ( )
 (setq n (length gdjc))
 (setq i 0)
 (while (< i n)
  (setq j1 (nth 0 (nth i gdjc)) j2 (nth 1 (nth i gdjc)))
  (setq p1 (list (* 0.5 (+ (car (cadr (assoc j1 gdzb))) (car (
           cadr (assoc j2 gdzb))))) 107.0))
  (setq gdj (nth 2 (nth i gdjc)))
  (cond ((= gdj "SO") (setq jc "素土夯实"))
        ((= gdj "S") (setq jc "砂石基础"))
        ((= gdj "SA") (setq jc "砂桩基础"))
        ((= gdj "SVC") (setq jc "混凝土桩基础"))
        ((= gdj "W") (setq jc "木桩基础"))
  )
  (command "color" "1")
  (command "text" "c" p1 "5" "0" jc)
  (command "color" "2")
  (command "line" (list (car (cadr (assoc j2 gdzb))) 105.0)
         (list (car (cadr (assoc j2 gdzb))) 115.0) "")
  (setq i (+ i 1))
 )
)

(defun hbg ( )
  (setq mxnh (float (- (fix minh) 4)))
  (setq p3 (list 124.0 (+ (* 10.0 (- mxnh minh)) (cadr pt0))))
  (setq d "t" c 0.0)
  (while d
   (setq p1 (list 124.0 (+ c (cadr p3))))
   (setq p2 (list 124.0 (+ 10.0 (cadr p1))))
   (command "color" "3")
   (command "pline" p1 "w" "2.0" "" p2 "")
   (setq c (+ c 20.0))
   (if (> c (- maxh (cadr p3))) (setq d nil))
  )
  (setq p4 p2)
  (command "line" (list 125.0 (cadr p3)) (list 125.0 (cadr p4))
   (list 123.0 (cadr p4)) (list 123.0 (cadr p3)) "c" )
  (setq n (fix (* 0.1 (- (cadr p4) (cadr p3)))))
  (setq c 0.0)
  (setq i 0)
  (while (< i (+ n 1))
   (setq p5 (list 121.5 (+ c (cadr p3))))
   (command "color" "1")
   (command "text" "r" p5 "2.5" "0" (rtos (fix (+ mxnh i)) 2 2))
   (setq c (+ c 10.0))
   (setq i (+ i 1))
  )
)

(defun hfb ( )
 (setq n (length gdzb))
 (setq i 0)
 (while (< i n)
  (setq j (substr (car (nth i gdzb)) 1 1))
  (setq p1 (cadr (nth i gdzb)) p2 (nth i jd))
  (cond (( or (= j "F") (= j "B")) (command "color" "2")
        (command "line" (list (+ (car p1) 1.5) (- (cadr p1) 1.5))
        (list (+ (car p1) 1.5) (cadr p2)) (list (- (car p1)
        1.5) (cadr p2)) (list (- (car p1) 1.5) (- (cadr p1)
        1.5)) "c")  (command "pline" (list (- (car p1) 2.5) (- (
        cadr p1) 2.0)) "w" "0.5" "" (list (+ (car p1) 2.5) (- (
                                 cadr p1) 2.0)) ""))
  )
  (setq i (+ i 1))
 )
)

(defun hjcgd ( )
 (SETVAR "DIMEXO" 3.0)
 (setvar "DIMEXE" 3.0)
 (setvar "DIMTSZ" 0)
 (setvar "DIMTXT" 2.50)
 (setvar "DIMTAD" 1)
 (setvar "DIMASZ" 1.0)
;; (command "dim" "dimblk" "xx0" "exit")
 (setq n (length jcgd))
 (setq i 0)
 (while (< i n)
  (setq jcd (nth i jcgd))
  (setq j (nth 0 jcd) jl (nth 1 jcd) nx (nth 2 jcd) 
        gj (nth 3 jcd) bg (nth 4 jcd) glch (nth 5 jcd))
  (setq p1 (list (+ (* k jl) (car (cadr (assoc j gdzb)))) (+ (* 10.0
           (- bg minh)) (cadr pt0))))
  (setq nn (strlen gj) )
  (if (= (substr  gj 2 1) "N") (setq cj (* 0.001   (atof (substr
   gj 3 (- nn 2))))) (setq cj (* 0.001   (atof (substr gj 2 (- nn
   1))))))
  (command "color" "4")
  (cond ((= nx "GS" ) (command "ellipse" "c" p1 (list (+ (car p1)
        (* 2.5 cj)) (cadr p1)) (* 5.0 cj)) 

        (command "color" "6")                       
        (command "text" (list (- (car p1) 1.0) 196.0) "3.5" "90" 
        "给水管道 管径")
        (command "insert" "c:/jiangdh/tl/bgfh1"
                (list (+ (+ (car p1) (* 2.5 cj)) 4.02) (cadr p1)) 
                "0.01" "0.01" "")
        (setq pta (list (car p1) (+ (cadr p1) (* 5.0 cj))))
        (command "color" "white")
        (command "text"  
                (list (+ (+ (car p1) (* 2.5 cj)) 4.02) (+ (cadr p1) 2.8))
                "2.5" "0" (rtos bg 2 2)))

        ((= nx "WS") (command "ellipse" p1 (list (car p1) (+ (
        cadr p1) (* 10.0 cj))) (* 2.5 cj)) 
        (command "color" "6")
                         
        (command "text" (list (- (car p1) 1.0) 196.0) "3.5" "90" 
        "污水管道 管径 ")
        (command "insert" "c:/jiangdh/tl/bgfh1" 
                (list (+ (car p1) 3.88) (cadr p1)) "0.01" "0.01" "")
        (setq pta (list (car p1) (+ (cadr p1) (* 10.0 cj))))
        (command "color" "white")
        (command "text"  
                (list (+ (car p1) 3.88) (+ (cadr p1) 2.8))
                "2.5" "0" (rtos bg 2 2)))
                        
        ((= nx "XH" ) (command "ellipse" "c" p1 (list (+ (car p1)
        (* 2.5 cj)) (cadr p1)) (* 5.0 cj)) 
        (command "color" "6")
                             
        (command "text" (list (- (car p1) 1.0) 196.0) "3.5" "90" 
        "循环水管道 管径")
        (command "insert" "c:/jiangdh/tl/bgfh1"
                (list (+ (+ (car p1) (* 2.5 cj)) 4.02) (cadr p1)) 
                "0.01" "0.01" "")
        (setq pta (list (car p1) (+ (cadr p1) (* 5.0 cj))))
        (command "color" "white")
        (command "text"  
                (list (+ (+ (car p1) (* 2.5 cj)) 4.02) (+ (cadr p1) 2.8))
                "2.5" "0" (rtos bg 2 2)))

        ((= nx "YS" ) (command "ellipse" p1 
        (list (car p1) (+ (cadr p1) (* 10.0 cj))) (* 2.5 cj)) 
        (command "color" "6")
                         
        (command "text" (list (- (car p1) 1.0) 196.0) "3.5" "90" 
        "雨水管道 管径")
        (command "insert" "c:/jiangdh/tl/bgfh1" 
                (list (+ (car p1) 3.88) (cadr p1)) "0.01" "0.01" "")
        (setq pta (list (car p1) (+ (cadr p1) (* 10.0 cj))))
        (command "color" "white")
        (command "text"  
                (list (+ (car p1) 3.88) (+ (cadr p1) 2.8))
                "2.5" "0" (rtos bg 2 2)))

        ((= nx "DL" ) (command "ellipse" p1 
        (list (car p1) (+ (cadr p1) (* 10.0 cj))) (* 2.5 cj)) 
        (command "color" "6")
                         
        (command "text" (list (- (car p1) 1.0) 196.0) "3.5" "90" 
        "动力管道 管径")
        (command "insert" "c:/jiangdh/tl/bgfh1" 
                (list (+ (car p1) 3.88) (cadr p1)) "0.01" "0.01" "")
        (setq pta (list (car p1) (+ (cadr p1) (* 10.0 cj))))
        (command "color" "white")
        (command "text"  
                (list (+ (car p1) 3.88) (+ (cadr p1) 2.8))
                "2.5" "0" (rtos bg 2 2)))

        ((= nx "RQ" ) (command "ellipse" p1 
        (list (car p1) (+ (cadr p1) (* 10.0 cj))) (* 2.5 cj)) 
        (command "color" "6")
                         
        (command "text" (list (- (car p1) 1.0) 196.0) "3.5" "90" 
        "燃气管道 管径")
        (command "insert" "c:/jiangdh/tl/bgfh1" 
                (list (+ (car p1) 3.88) (cadr p1)) "0.01" "0.01" "")
        (setq pta (list (car p1) (+ (cadr p1) (* 10.0 cj))))
        (command "color" "white")
        (command "text"  
                (list (+ (car p1) 3.88) (+ (cadr p1) 2.8))
                "2.5" "0" (rtos bg 2 2)))
        
        ((= nx "TX" ) (command "ellipse" p1 
        (list (car p1) (+ (cadr p1) (* 10.0 cj))) (* 2.5 cj)) 
        (command "color" "6")
                         
        (command "text" (list (- (car p1) 1.0) 196.0) "3.5" "90" 
        "通信管道 管径")
        (command "insert" "c:/jiangdh/tl/bgfh1" 
                (list (+ (car p1) 3.88) (cadr p1)) "0.01" "0.01" "")
        (setq pta (list (car p1) (+ (cadr p1) (* 10.0 cj))))
        (command "color" "white")
        (command "text"  
                (list (+ (car p1) 3.88) (+ (cadr p1) 2.8))
                "2.5" "0" (rtos bg 2 2)))
  )

  (command "color" "6")
;;  (command "line" (list (car p1) ( + (cadr p1) (* cj 0.5))) (list (car p1
;;                 ) 175.0) "")
  (command "line" pta (list (car p1) 175.0) "")
  (command "text" (list (- (car p1) 1.0) 221.5) "2.5" "90" gj)
  (command "text" (list (- (car p1) 1.0) 179.0) "2.5" "90" glch)
;; (command "text" (list (- (car p1) 1.0) 246.0) "2.5" "90" (rtos
;;                                                    bg 2 3))
;;  (command "dim1" "hor" (list (car p1) (- (cadr p1) 10.0)) (list
;;   (- (car p1) (* k jl)) (- (cadr p1) 10.0)) (list (car p1) (- (
;;   cadr p1) 10.0)) (rtos (abs jl) 2 3))
  (setq i (+ i 1))
 )
)

(defun c:gsdat ( )
 (textscr)
 (setq jk (getvar "DWGNAME"))
 (setq sjk (getstring t (strcat "\n 建立数据文件< " jk " >: ")))
 (if (= sjk "") (setq sjk jk))
 (setq sj sjk)
 (setq b (dm1))
 (setq a (chx1 b))
 (prt1 a) (princ)
 (initget 1 "Y N")
 (setq xg (getkword "\n 需要修改吗? (Y/N): "))
 (while (= xg "Y")
  (setq b a) (setq a (chx1 b)) (prt1 a) (princ)
  (initget 1 "Y N")
  (setq xg (getkword "\n 需要修改吗? (Y/N): ")))
 (setq sjk (open (strcat sj ".dat") "w"))
 (write-line "ground-control-points" sjk)
 (write-line "No:____Dist____Elev" sjk)
 (setq n (length a))
 (setq i 0)
 (while (< i n)
  (write-line (strcat (itoa (+ i 1)) "____" (rtos (car (cadr (nth
  i a))) 2 2) "____" (rtos (cadr (cadr (nth i a))) 2 2)) sjk)
  (setq i (+ i 1))
 )
 (close sjk)
 (sg1) (chx2) (prt2)
 (initget 1 "Y N")
 (setq xg (getkword "\n 需要修改吗? (Y/N): "))
 (while (= xg "Y")
  (chx2) (prt2)
  (initget 1 "Y N")
  (setq xg (getkword "\n 再需要修改吗? (Y/N): ")))
 (setq sjk (open (strcat sj  ".dat") "a"))
 (write-line "control-points-pipeline" sjk)
 (write-line "No:____Dist____Meters____Depth____Character" sjk)
 (write-line (strcat j1 "____0.00" "____" lch0 "____" 
             (rtos gs0 2 2) "____" jtd0 ) sjk)
 (setq n (length jb))
 (setq i 0)
 (while (< i n)
;;  (if (<= (nth i spzjb) pi) (setq spzj (angtos (nth i spzjb) 0 2))
;;      (setq spzj (rtos (* -1.0 (atof (angtos (- (* 2 pi) (nth i spzjb))
;;      0 2))) 2 2)))
  (write-line (strcat (nth i jb) "____" (rtos (nth i jlb) 2 2) "____"
       (nth i lchb) "____" (rtos (nth i gsb) 2 2) 
       "____" (nth i jtdb)) sjk)
  (setq i (+ i 1))
  )
 (close sjk)
 (gjgc1)
 (setq sjk (open (strcat sj ".dat") "a"))
 (write-line "diameter---material" sjk)
 (write-line "No:____ToNo:____Diameter____Material" sjk)
 (setq n (length gjgc))
 (setq i 0)
 (while (< i n)
  (write-line (strcat (car (nth i gjgc)) "____" (nth 1 (nth i gjgc))
  "____" (nth 2 (nth i gjgc)) "____" (nth 3 (nth i gjgc))) sjk)
  (setq i (+ i 1))
 )
 (close sjk)
;; (gdjc1)
 (setq sjk (open (strcat sj ".dat") "a"))
;; (write-line "base-pipeline" sjk)
;; (write-line "No:____ToNo:____Base" sjk)
;; (setq n (length gdjc))
;; (setq i 0)
;; (while (< i n)
;;  (write-line (strcat (car (nth i gdjc)) "____" (nth 1 (nth i gdjc))
;;              "____" (nth 2 (nth i gdjc))) sjk)
;;  (setq i (+ i 1))
;; )
 (write-line "cross-points" sjk)
 (write-line "No:____Dist____Type____Diameter____Elev____Meters" sjk)
 (close sjk)
 (initget 1 "Y N")
 (setq jc (getkword "\n 需要画过路管道吗? (Y/N): "))
 (cond ((= jc "Y") (jcgd1)
 (setq sjk (open (strcat sj ".dat") "a"))
 (setq n (length jcgd))
 (setq i 0)
 (while (< i n)
  (setq jcg (nth i jcgd))
  (write-line (strcat (car jcg) "____" (rtos (nth 1 jcg) 2 2)
  "____" (nth 2 jcg) "____" (nth 3 jcg) "____" (rtos (nth 4 jcg)
              2 2) "____" (nth 5 jcg)) sjk)
  (setq i (+ i 1))
 )
 (close sjk)))
 (setq sjk (open (strcat sj ".dat") "a"))
 (write-line "input-end" sjk)
 (close sjk)
)

(defun ss (gs)
 (setq n (strlen gs))
 (setq ii 1) (setq kk2 nil)
 (setq i 2)
 (while (<= i n)
  (setq kk (substr gs i 1)) (setq mm (substr gs (- i 1) 1))
  (cond ((and (= kk "_") (/= mm "_"))
  (setq kk1 (substr gs ii (- i ii)))
  (setq kk2 (cons kk1 kk2))
  (setq ii (+ i 4))
        )
  )
  (setq i (+ i 1))
 )
 (setq kk2 (cons (substr gs ii (- (+ n 1) ii)) kk2))
 (reverse kk2)
)

(defun c:outdat ()
 (setq jp (getvar "DWGNAME"))
 (setq jk (getstring t (strcat "\n 读取数据文件 <" jp ">: ")))
 (if (= jk "") (setq jk jp))
 (setq sjk (open (strcat jk ".dat") "r"))
 (setq a nil jb nil jlb nil lchb nil gsb nil jtdb nil 
       gjgc nil gdjc nil jcgd nil z nil)
 (setq d "t")
 (while d
  (setq sj (read-line sjk)) (setq jj (ss sj))
  (cond ((= sj "ground-control-points") (setq js "h1")))
  (cond ((= sj "control-points-pipeline") (setq js "h2")))
  (cond ((= sj "diameter---material") (setq js "h3")))
;;  (cond ((= sj "base-pipeline") (setq js "h4")))
  (cond ((= sj "cross-points") (setq js "h5")))
  (cond ((= sj "input-end") (setq js "h6")))
  (cond ((= js "h1")
    (if (or (= sj "ground-control-points")
    (= sj "No:____Dist____Elev")) (setq yy "k1") (setq yy "k2"))
    (if (= yy "k2") (setq a (cons (list (read (car jj)) 
        (list (read (nth 1 jj)) (read (nth 2 jj)))) a)))
        ))
  (cond ((= js "h2") (if (or (= sj "No:____Dist____Meters____Depth____Character")
        (= sj "control-points-pipeline")) (setq yy "k1") (setq yy "k2"))
              (cond ((= yy "k2") (setq jb (cons (car jj) jb)) (setq jlb
              (cons (read (nth 1 jj)) jlb)) 
              (setq lchb (cons (nth 2 jj) lchb))
              (setq gsb (cons (read (nth 3 jj)) gsb)) 
              (setq jtdb (cons (last jj) jtdb)))
;;              (if (< (read (last jj)) 0.0) (setq zj (+
;;              (read (last jj)) 360.0)) (setq zj (read (last jj))))
;;              (setq spzjb (cons (dtr zj) spzjb)))
        )))
  (cond ((= js "h3") (if (or (= sj "diameter---material")
        (= sj "No:____ToNo:____Diameter____Material")) (setq yy "k1") (setq yy "k2"))
        (if (= yy "k2") (setq gjgc (cons jj gjgc)))
        ))
;;  (cond ((= js "h4") (if (or (= sj "No:____ToNo:____Base")
;;        (= sj "base-pipeline")) (setq yy "k1") (setq yy "k2"))
;;        (if (= yy "k2") (setq gdjc (cons jj gdjc)))
;;        ))
  (cond ((= js "h5") (if (or (= sj "cross-points")
        (= sj "No:____Dist____Type____Diameter____Elev____Meters"))
        (setq yy "k1") (setq yy "k2"))
         (cond ((= yy "k2") (setq jcgd (cons (list (car jj) (read
         (nth 1 jj)) (nth 2 jj) (nth 3 jj) (read (nth 4 jj))
         (last jj)) jcgd)))
        )))
  (cond ((= js "h6") (close sjk) (setq d nil)))
 )
 (setq a (reverse a) jb (reverse jb) jlb (reverse jlb) 
 lchb (reverse lchb) gsb (reverse gsb)
 jtdb (reverse jtdb) gjgc (reverse gjgc) gdjc (reverse gdjc)
 jcgd (reverse jcgd)) 
 (setq z (mapcar 'list jb (mapcar 'list jlb lchb gsb jtdb)))
)

(defun c:hgjgc ()
 (gjgc1) (hgjgc))

;;(defun c:hgdjc ()
;; (gdjc1) (hgdjc))

(defun c:hjcgd ()
 (jcgd1) (hjcgd))

(defun C:gspm ()
 (prompt "\n\t***************************************************************")
 (prompt "\n\t*                                                             *")
 (prompt "\n\t*                     绘制给水纵断面图                        *")
 (prompt "\n\t*                                                             *")
 (prompt "\n\t***************************************************************")
 (textscr)
 (command "style" "standard" "romans,hztxt" "" "" "" "" "" "")
 (setvar "APERTURE" 1)
 (setvar "PICKBOX" 1)
 (setvar "BLIPMODE" 0) (c:outdat)
 (setq bl (getreal
 "\n 请输入绘画纵向比例(1000,500...): "))
 (setq bl00 (rtos bl 2 2))
       (setq k (/ 1000.0 bl))
 (setq pd0 (getpoint "\n 管道起点座标(135,280): "))
  (if (= pd0 nil) (setq pd0 '(135 280)))
 (tk) (dm2) (nk) (sg2) (setq g (sg2)) (setq h (dm2))
 (sg3 g h) 
 (hdmx) 
 (hsgx) 
 (hcx) 
 (hgjgc) 
 (hjdtz)
;; (hgdjc)
 (hfb) 
 (hbg) 
 (if (/= jcgd nil) (hjcgd)) 
;; (hjddy)
 (if (= bl00 "1000.00") 
     (command "insert" "c:/jiangdh/tl/bl1" '(62 222) "" "" "")
 )
 (if (= bl00 "500.00")
     (command "insert" "c:/jiangdh/tl/bl5" '(62 222) "" "" "")
 )
 (if (= bl00 "1000") 
     (command "insert" "c:/jiangdh/tl/bl1" '(62 222) "" "" "")
 )
 (if (= bl00 "500")
     (command "insert" "c:/jiangdh/tl/bl5" '(62 222) "" "" "")
 )
 (setvar "APERTURE" 7)
 (setvar "PICKBOX" 7)
)

(defun c:gspm2 ()
 (textscr)
 (setvar "APERTURE" 1) (setvar "PICKBOX" 1) (setvar "BLIPMODE" 0)
 (prompt "\n\t\t局部绘制给水纵断面图")
 (prompt "\n\t\************************************************************")
 (C:OUTDAT)
 (setq bl (getreal
  "\n 请输入绘图纵向比例(1000,500...): "))
     (setq k (/ 1000.0 bl))
 (setq pd0 (getpoint "\n 管道起点座标(135,280): "))
  (if (= pd0 nil) (setq pd0 '(125 280))) (dm2)
  (command "move" "w" '(60.0 50.0) (list (- cd 20.0) (- kd 15.0))
          "" '(0.0 0.0) (list (car (last (dm2))) 0.0))
  (nk) (sg2) (setq g (sg2)) (setq h (dm2))
  (sg3 g h) (hdmx) (hsgx) (hcx) (hgjgc) (hgdjc) (hfb) (hbg)
  (if (/= jcgd nil) (hjcgd)) (hjddy)
  (setvar "APERTURE" 7)
  (setvar "PICKBOX" 7)
)

(textscr)
(princ "\n\n\t  给水纵断程序已加载，作者：张健君等。\n")
(princ "\n\t  启动命令：\n")
(princ "\n\t  建立数据文件：GSDAT")
(princ "\n\t  绘图命令：GSPM。\n")
(princ)






�

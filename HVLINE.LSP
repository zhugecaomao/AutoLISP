(DEFUN HLINE()
(SETQ LMAX (GETVAR "EXTMAX"))
(SETQ LMIN (GETVAR "EXTMIN"))
(SETQ DRP  (GETPOINT"\nSELECT A POINT TO DRAW A EXTLINE: "))
(SETQ DR1 (LIST (CAR LMAX) (CADR DRP)))
(SETQ DR2 (LIST (CAR LMIN) (CADR DRP)))
(COMMAND "LINE" DR1 DR2 "")
)
(DEFUN VLINE()
(SETQ LMAX (GETVAR "EXTMAX"))
(SETQ LMIN (GETVAR "EXTMIN"))
(SETQ DRP  (GETPOINT"\nSELECT A POINT TO DRAW A EXTLINE: "))
(SETQ DR1 (LIST (CAR DRP) (CADR LMAX)))
(SETQ DR2 (LIST (CAR DRP) (CADR LMIN)))
(COMMAND "LINE" DR1 DR2 "")
)

(DEFUN C:INT-MM ()
   (SETVAR "CMDECHO" 0)
   (SETQ VC (GETVAR "VIEWCTR"))
   (SETQ YR (GETVAR "VIEWSIZE"))
   (SETQ XR (* YR 1.3864))
   (SETQ YD (/ YR 3))
   (SETQ XD (/ XR 8))
   (SETQ XB (- (CAR VC) (/ XR 2)))
   (SETQ YB (- (CADR VC) (/ YR 2)))
   (COMMAND "VSLIDE" "C:/ACAD/SLIDE/INT-MM")
;----
   (SETQ PT (GETPOINT "\nPLEASE DIGIT THE CHAR. TABLE : "))
             (SETQ XP (CAR PT))
             (SETQ YP (CADR PT))
             (SETQ XAA (- XP XB))
             (SETQ YAA (- YP YB))
             (SETQ XA (ABS XAA))
             (SETQ YA (ABS YAA))
             (SETQ X (FIX ( / XA XD)))
             (SETQ Y (FIX ( / YA YD)))
;
      (IF (AND (= X 0) (= Y 0))
      (COMMAND "REDRAW" "INSERT" "C:/ACAD/BLOCK/INT150-1" PAUSE 1 1))
      (IF (AND (= X 1) (= Y 0))
      (COMMAND "REDRAW" "INSERT" "C:/ACAD/BLOCK/INT150-2" PAUSE 1 1))
      (IF (AND (= X 2) (= Y 0))
      (COMMAND "REDRAW" "INSERT" "INT150-1=C:/ACAD/BLOCK/INT150-3" PAUSE 1 1 0 ))
      (IF (AND (= X 3) (= Y 0))
      (COMMAND "REDRAW" "INSERT" "INT150-2=C:/ACAD/BLOCK/INT150-3" PAUSE 1 1 0 ))
      (IF (AND (= X 4) (= Y 0))
      (COMMAND "REDRAW" "INSERT" "C:/ACAD/BLOCK/INT150-4" PAUSE 1 1))
      (IF (AND (= X 5) (= Y 0))
      (COMMAND "REDRAW" "INSERT" "C:/ACAD/BLOCK/INT150-5" PAUSE 1 1))
      (IF (AND (= X 6) (= Y 0))
      (COMMAND "REDRAW" "INSERT" "C:/ACAD/BLOCK/INT150-6" PAUSE 1 1))
      (IF (AND (= X 7) (= Y 0))
      (COMMAND "REDRAW" "INSERT" "C:/ACAD/BLOCK/INT150-7" PAUSE 1 1))
     (IF (AND (= X 0) (= Y 1))
      (COMMAND "REDRAW" "INSERT" "C:/ACAD/BLOCK/INT100-1" PAUSE 1 1))
      (IF (AND (= X 1) (= Y 1))
      (COMMAND "REDRAW" "INSERT" "C:/ACAD/BLOCK/INT100-2" PAUSE 1 1))
      (IF (AND (= X 2) (= Y 1))
      (COMMAND "REDRAW" "INSERT" "INT100-1=C:/ACAD/BLOCK/INT100-3"""))
      (IF (AND (= X 3) (= Y 1))
      (COMMAND "REDRAW" "INSERT" "INT100-2=C:/ACAD/BLOCK/INT100-3"""))
      (IF (AND (= X 4) (= Y 1))
      (COMMAND "REDRAW" "INSERT" "C:/ACAD/BLOCK/INT100-4" PAUSE 1 1))
      (IF (AND (= X 5) (= Y 1))
      (COMMAND "REDRAW" "INSERT" "C:/ACAD/BLOCK/INT100-5" PAUSE 1 1))
      (IF (AND (= X 6) (= Y 1))
      (COMMAND "REDRAW" "INSERT" "C:/ACAD/BLOCK/INT100-6" PAUSE 1 1))
      (IF (AND (= X 7) (= Y 1))
      (COMMAND "REDRAW" "INSERT" "C:/ACAD/BLOCK/INT100-7" PAUSE 1 1))
      (IF (AND (= X 0) (= Y 2))
      (COMMAND "REDRAW" "INSERT" "C:/ACAD/BLOCK/INT50-1" PAUSE 1 1))
      (IF (AND (= X 1) (= Y 2))
      (COMMAND "REDRAW" "INSERT" "C:/ACAD/BLOCK/INT50-2" PAUSE 1 1))
      (IF (AND (= X 2) (= Y 2))
      (COMMAND "REDRAW" "INSERT" "INT50-1=C:/ACAD/BLOCK/INT50-3"""))
      (IF (AND (= X 3) (= Y 2))
      (COMMAND "REDRAW" "INSERT" "INT50-2=C:/ACAD/BLOCK/INT50-3"""))
      (IF (AND (= X 4) (= Y 2))
      (COMMAND "REDRAW" "INSERT" "C:/ACAD/BLOCK/INT50-4" PAUSE 1 1))
      (IF (AND (= X 5) (= Y 2))
      (COMMAND "REDRAW" "INSERT" "C:/ACAD/BLOCK/INT50-5" PAUSE 1 1))
      (IF (AND (= X 6) (= Y 2))
      (COMMAND "REDRAW" "INSERT" "C:/ACAD/BLOCK/INT50-6" PAUSE 1 1))
      (IF (AND (= X 7) (= Y 2))
      (COMMAND "REDRAW" "INSERT" "C:/ACAD/BLOCK/INT50-7" PAUSE 1 1))
      )

(defun c:int()
;  (setvar "CMDECHO" 0)
;  (setq la (getvar "clayer"))
;  (command "layer" "m" "text" "c" "6" "" "")
   (princ "\nChoose Two Line: ")
   (setq BB (ssget))
  (setq bb1 (entget (ssname BB 0)))
  (setq l11 (cdr (assoc 10 bb1)))
  (setq l12 (cdr (assoc 11 bb1)))
  (setq bb2 (entget (ssname a 1)))
  (setq l21 (cdr (assoc 10 bb2)))
  (setq l22 (cdr (assoc 11 bb2)))
  (setq p (inters l11 l12 l21 l22 nil))
;      (command "setvar" "pdmode" "0")
;      (command "setvar" "pdsize" "3")
      (command "point" p)
;      (command "layer" "S" draw "")
)

(defun c:inter()
;  (setvar "CMDECHO" 0)
;  (setq la (getvar "clayer"))
;  (command "layer" "m" "text" "c" "6" "" "")
   (princ "\nChoose Two Line: ")
   (setq abc (ssget))
  (setq bbb1 (entget (ssname abc 0)))
  (setq lll11 (cdr (assoc 10 bbb1)))
  (setq lll12 (cdr (assoc 11 bbb1)))
  (setq bbb2 (entget (ssname abc 1)))
  (setq lll21 (cdr (assoc 10 bbb2)))
  (setq lll22 (cdr (assoc 11 bbb2)))
  (setq p (inters lll11 lll12 lll21 lll22 nil))
;      (command "setvar" "pdmode" "0")
;      (command "setvar" "pdsize" "3")
      (command "point" p)
;      (command "layer" "S" draw "")
)

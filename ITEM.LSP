(DEFUN C:ITEM()
;(IF (= (TYPE F1) 'FILE ) "YES"  (STOP))
;(IF (= (TYPE F2) 'FILE ) "YES" (STOP))
(SETQ TZO (GETVAR "TEXTSIZE"))
(PROMPT"\nENTER TEXT HEIGHT:<")(PRIN1 TZO)(PROMPT">")
(SETQ TZ (GETREAL))
(IF (= TZ NIL)
    (SETQ TZ TZO)
)
(SETQ TXT (GETSTRING "\n TYPE THE STRINGS:"))
(SETQ P2 (GETPOINT "\n LOCATE BALLOON CENTER: "))
(COMMAND "TEXT" "C" (LIST (CAR P2) (- (CADR P2) (/ TZ 2))) TZ "0" TXT)
(IF (> (STRLEN TXT) 2)
    (COMMAND "CIRCLE" P2 (* TZ 1.6))
    (COMMAND "CIRCLE" P2 (* TZ 1.2))
)
)

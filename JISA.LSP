(DEFUN C:JISA()
  (MENUCMD "S=JISA")
  (SETQ LY (GETVAR "CLAYER"))
  (SETQ P1 (GETPOINT"\nINPUT A POINT:"))
  (SETQ P2 (GETPOINT P1"\nINPUT A POINT:"))
; (SETQ E (DISTANCE P1 P2))
  (SETQ L (GETREAL"\nHOW LONGER:"))
  (SETQ AG1 (ANGLE P1 P2))
  (SETQ AG2 (* PI 0.5))
  (IF (AND (>= L 4) (< L 60))
      (PROGN
         (SETQ A 8.5)
         (SETQ B 16)
         (SETQ C 17)
         (SETQ E 32)
         (SETQ H 9)
      )
  )

  (SETQ P2 (POLAR P1 AG1 E))
  (SETQ DR1 (POLAR P1 (+ AG1 (DTR 90)) (/ L 2.0)))
  (SETQ DR2 (POLAR P1 (- AG1 (DTR 90)) (/ L 2.0)))
  (SETQ P3 (POLAR P1 AG1 (/ (- E C) 2.0)))
  (SETQ DR3 (POLAR P3 (+ AG1 (DTR 90)) (/ L 2.0)))
  (SETQ DR4 (POLAR P3 (- AG1 (DTR 90)) (/ L 2.0)))
  (SETQ P4 (POLAR P2 AG1 (* (/ (- E C) 2.0) -1)))
  (SETQ DR5 (POLAR P4 (+ AG1 (DTR 90)) (/ L 2.0)))
  (SETQ DR6 (POLAR P4 (- AG1 (DTR 90)) (/ L 2.0)))
  (SETQ DR7 (POLAR P2 (+ AG1 (DTR 90)) (/ L 2.0)))
  (SETQ DR8 (POLAR P2 (- AG1 (DTR 90)) (/ L 2.0)))
  (SETQ DR9 (POLAR DR1 AG1 (/ E 2.0)))
  (SETQ DR10 (POLAR DR2 AG1 (/ E 2.0)))
  (SETQ DR11 (POLAR DR9 (+ AG1 (DTR 90)) (+ B 1)))
  (SETQ DR12 (POLAR DR10 (- AG1 (DTR 90)) (+ B 1)))
  (SETQ DR13 (POLAR DR9  AG1 (+ (/ E 2.0) 1)))
  (SETQ DR14 (POLAR DR9  AG1 (* (+ (/ E 2.0) 1) -1)))
  (SETQ DR15 (POLAR DR10 AG1 (+ (/ E 2.0) 1)))
  (SETQ DR16 (POLAR DR10 AG1 (* (+ (/ E 2.0) 1) -1)))
  (COMMAND "LINE" DR1 DR2 "")
  (COMMAND "LINE" DR3 DR4 "")
  (COMMAND "LINE" DR5 DR6 "")
  (COMMAND "LINE" DR7 DR8 "")
  (COMMAND "ARC" DR5 "E" DR3 "R" A)
  (COMMAND "ARC" DR4 "E" DR6 "R" A)
  (COMMAND "ARC" DR7 "E" DR1 "R" B)
  (COMMAND "ARC" DR2 "E" DR8 "R" B)
  (COMMAND "LAYER" "S" "CEN" "")
  (COMMAND "LINE" DR11 DR12 "")
  (COMMAND "LINE" DR13 DR14 "")
  (COMMAND "LINE" DR15 DR16 "")
  (COMMAND "LAYER" "S" LY "")
)

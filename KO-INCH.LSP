(DEFUN C:KO-INCH ()
   (SETVAR "CMDECHO" 0)
   (SETQ VC (GETVAR "VIEWCTR"))
   (SETQ YR (GETVAR "VIEWSIZE"))
   (SETQ XR (* YR 1.3864))
   (SETQ YD (/ YR 3))
   (SETQ XD (/ XR 8))
   (SETQ XB (- (CAR VC) (/ XR 2)))
   (SETQ YB (- (CADR VC) (/ YR 2)))
   (COMMAND "VSLIDE" "C:/ACAD/SLIDE/KO-IN")
;----
   (SETQ PT (GETPOINT "\nPLEASE DIGIT THE CHAR. TABLE : "))
             (SETQ XP (CAR PT))
             (SETQ YP (CADR PT))
             (SETQ XAA (- XP XB))
             (SETQ YAA (- YP YB))
             (SETQ XA (ABS XAA))
             (SETQ YA (ABS YAA))
             (SETQ X (FIX ( / XA XD)))
             (SETQ Y (FIX ( / YA YD)))
;
      (IF (AND (= X 0) (= Y 1))
      (COMMAND "REDRAW" "INSERT" "C:/ACAD/BLOCK/KO15" PAUSE 1 1 0))
      (IF (AND (= X 1) (= Y 1))
      (COMMAND "REDRAW" "INSERT" "C:/ACAD/BLOCK/KO15-1" PAUSE 1 1 0))
      (IF (AND (= X 2) (= Y 1))
      (COMMAND "REDRAW" "INSERT" "C:/ACAD/BLOCK/KO15-2" PAUSE 1 1))
      (IF (AND (= X 3) (= Y 1))
      (COMMAND "REDRAW" "INSERT" "C:/ACAD/BLOCK/KO15-3" PAUSE 1 1))
      (IF (AND (= X 4) (= Y 1))
      (COMMAND "REDRAW" "INSERT" "C:/ACAD/BLOCK/KO15-4" PAUSE 1 1))
      (IF (AND (= X 5) (= Y 1))
      (COMMAND "REDRAW" "INSERT" "C:/ACAD/BLOCK/KO15-5" PAUSE 1 1))
      (IF (AND (= X 6) (= Y 1))
      (COMMAND "REDRAW" "INSERT" "C:/ACAD/BLOCK/KO15-7" PAUSE 1 1))
      (IF (AND (= X 7) (= Y 1))
      (COMMAND "REDRAW" "INSERT" "C:/ACAD/BLOCK/KO15-9" PAUSE 1 1))
      (IF (AND (= X 0) (= Y 2))
      (COMMAND "REDRAW" "INSERT" "C:/ACAD/BLOCK/KO125" PAUSE 1 1 0))
      (IF (AND (= X 1) (= Y 2))
      (COMMAND "REDRAW" "INSERT" "C:/ACAD/BLOCK/KO125-1" PAUSE 1 1 0))
      (IF (AND (= X 2) (= Y 2))
      (COMMAND "REDRAW" "INSERT" "C:/ACAD/BLOCK/KO125-2" PAUSE 1 1))
      (IF (AND (= X 3) (= Y 2))
      (COMMAND "REDRAW" "INSERT" "C:/ACAD/BLOCK/KO125-3" PAUSE 1 1))
      (IF (AND (= X 4) (= Y 2))
      (COMMAND "REDRAW" "INSERT" "C:/ACAD/BLOCK/KO1250-4" PAUSE 1 1))
      (IF (AND (= X 5) (= Y 2))
      (COMMAND "REDRAW" "INSERT" "C:/ACAD/BLOCK/KO125-5" PAUSE 1 1))
      (IF (AND (= X 6) (= Y 2))
      (COMMAND "REDRAW" "INSERT" "C:/ACAD/BLOCK/KO125-7" PAUSE 1 1))
      (IF (AND (= X 7) (= Y 2))
      (COMMAND "REDRAW" "INSERT" "C:/ACAD/BLOCK/KO125-9" PAUSE 1 1))
      )

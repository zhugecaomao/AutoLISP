(DEFUN C:KO-MM ()
   (SETVAR "CMDECHO" 0)
   (SETQ VC (GETVAR "VIEWCTR"))
   (SETQ YR (GETVAR "VIEWSIZE"))
   (SETQ XR (* YR 1.3864))
   (SETQ YD (/ YR 3))
   (SETQ XD (/ XR 8))
   (SETQ XB (- (CAR VC) (/ XR 2)))
   (SETQ YB (- (CADR VC) (/ YR 2)))
   (COMMAND "VSLIDE" "C:/ACAD/SLIDE/KO-MM")
;----
   (SETQ PT (GETPOINT "\nPLEASE DIGIT THE CHAR. TABLE : "))
             (SETQ XP (CAR PT))
             (SETQ YP (CADR PT))
             (SETQ XAA (- XP XB))
             (SETQ YAA (- YP YB))
             (SETQ XA (ABS XAA))
             (SETQ YA (ABS YAA))
             (SETQ X (FIX ( / XA XD)))
             (SETQ Y (FIX ( / YA YD)))
;
      (IF (AND (= X 0) (= Y 0))
      (COMMAND "REDRAW" "INSERT" "C:/ACAD/BLOCK/KO40" PAUSE 1 1 0))
      (IF (AND (= X 1) (= Y 0))
      (COMMAND "REDRAW" "INSERT" "C:/ACAD/BLOCK/KO40-1" PAUSE 1 1 0))
      (IF (AND (= X 2) (= Y 0))
      (COMMAND "REDRAW" "INSERT" "C:/ACAD/BLOCK/KO40-2" PAUSE 1 1))
      (IF (AND (= X 3) (= Y 0))
      (COMMAND "REDRAW" "INSERT" "C:/ACAD/BLOCK/KO40-3" PAUSE 1 1))
      (IF (AND (= X 4) (= Y 0))
      (COMMAND "REDRAW" "INSERT" "C:/ACAD/BLOCK/KO40-4" PAUSE 1 1))
      (IF (AND (= X 5) (= Y 0))
      (COMMAND "REDRAW" "INSERT" "C:/ACAD/BLOCK/KO40-5" PAUSE 1 1))
      (IF (AND (= X 6) (= Y 0))
      (COMMAND "REDRAW" "INSERT" "C:/ACAD/BLOCK/KO40-7" PAUSE 1 1))
      (IF (AND (= X 7) (= Y 0))
      (COMMAND "REDRAW" "INSERT" "C:/ACAD/BLOCK/KO40-9" PAUSE 1 1))
      (IF (AND (= X 0) (= Y 1))
      (COMMAND "REDRAW" "INSERT" "C:/ACAD/BLOCK/KO35" PAUSE 1 1 0))
      (IF (AND (= X 1) (= Y 1))
      (COMMAND "REDRAW" "INSERT" "C:/ACAD/BLOCK/KO35-1" PAUSE 1 1 0))
      (IF (AND (= X 2) (= Y 1))
      (COMMAND "REDRAW" "INSERT" "C:/ACAD/BLOCK/KO35-2" PAUSE 1 1))
      (IF (AND (= X 3) (= Y 1))
      (COMMAND "REDRAW" "INSERT" "C:/ACAD/BLOCK/KO35-3" PAUSE 1 1))
      (IF (AND (= X 4) (= Y 1))
      (COMMAND "REDRAW" "INSERT" "C:/ACAD/BLOCK/KO35-4" PAUSE 1 1))
      (IF (AND (= X 5) (= Y 1))
      (COMMAND "REDRAW" "INSERT" "C:/ACAD/BLOCK/KO35-5" PAUSE 1 1))
      (IF (AND (= X 6) (= Y 1))
      (COMMAND "REDRAW" "INSERT" "C:/ACAD/BLOCK/KO35-7" PAUSE 1 1))
      (IF (AND (= X 7) (= Y 1))
      (COMMAND "REDRAW" "INSERT" "C:/ACAD/BLOCK/KO35-9" PAUSE 1 1))
      (IF (AND (= X 0) (= Y 2))
      (COMMAND "REDRAW" "INSERT" "C:/ACAD/BLOCK/KO30" PAUSE 1 1 0))
      (IF (AND (= X 1) (= Y 2))
      (COMMAND "REDRAW" "INSERT" "C:/ACAD/BLOCK/KO30-1" PAUSE 1 1 0))
      (IF (AND (= X 2) (= Y 2))
      (COMMAND "REDRAW" "INSERT" "C:/ACAD/BLOCK/KO30-2" PAUSE 1 1))
      (IF (AND (= X 3) (= Y 2))
      (COMMAND "REDRAW" "INSERT" "C:/ACAD/BLOCK/KO30-3" PAUSE 1 1))
      (IF (AND (= X 4) (= Y 2))
      (COMMAND "REDRAW" "INSERT" "C:/ACAD/BLOCK/KO30-4" PAUSE 1 1))
      (IF (AND (= X 5) (= Y 2))
      (COMMAND "REDRAW" "INSERT" "C:/ACAD/BLOCK/KO30-5" PAUSE 1 1))
      (IF (AND (= X 6) (= Y 2))
      (COMMAND "REDRAW" "INSERT" "C:/ACAD/BLOCK/KO40-7" PAUSE 1 1))
      (IF (AND (= X 7) (= Y 2))
      (COMMAND "REDRAW" "INSERT" "C:/ACAD/BLOCK/KO30-9" PAUSE 1 1))
      )

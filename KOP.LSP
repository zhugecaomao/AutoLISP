(DEFUN C:KOP()
(COMMAND "SETVAR" "HIGHLIGHT" "1")
(SETQ LY (GETVAR "CLAYER"))
(SETQ P1 (GETPOINT "\nCIRCLE CEND POINT:"))
(SETQ D1 (GETDIST P1 "\nDia1:"))
(COMMAND "LAYER" "SET" "DRAW" "")
(COMMAND "CIRCLE" P1 "D" D1)
(SETQ CP1 (LIST (CAR P1) (+ (CADR P1) (/ D1 2.0) 1)))
(SETQ CP2 (LIST (CAR P1) (- (CADR P1) (/ D1 2.0) 1)))
(SETQ CP3 (LIST (- (CAR P1) (/ D1 2.0) 1) (CADR P1)))
(SETQ CP4 (LIST (+ (CAR P1) (/ D1 2.0) 1) (CADR P1)))
(COMMAND "LAYER" "SET" "CENTER" "")
(COMMAND "LINE" CP1 CP2 "")
(COMMAND "LINE" CP3 CP4 "")
(COMMAND  "LAYER" "SET" "TEXT" "")
(SETQ TP (LIST (+ (CAR P1) 2) (+ (CADR P1) 2)))
(COMMAND  "TEXT" TP 3 0 "KO")
(COMMAND "SETVAR" "HIGHLIGHT" "1")
(COMMAND "LAYER" "SET" LY "")
)

(DEFUN C:L-INT-MM ()
   (SETVAR "CMDECHO" 0)
   (SETQ VC (GETVAR "VIEWCTR"))
   (SETQ YR (GETVAR "VIEWSIZE"))
   (SETQ XR (* YR 1.3864))
   (SETQ YD (/ YR 4))
   (SETQ XD (/ XR 3))
   (SETQ XB (- (CAR VC) (/ XR 2)))
   (SETQ YB (- (CADR VC) (/ YR 2)))
   (COMMAND "VSLIDE" "C:/ACAD/SLIDE/L-INT-MM")
;----
   (SETQ PT (GETPOINT "\nPLEASE DIGIT THE CHAR. TABLE : "))
             (SETQ XP (CAR PT))
             (SETQ YP (CADR PT))
             (SETQ XAA (- XP XB))
             (SETQ YAA (- YP YB))
             (SETQ XA (ABS XAA))
             (SETQ YA (ABS YAA))
             (SETQ X (FIX ( / XA XD)))
             (SETQ Y (FIX ( / YA YD)))
;
      (IF (AND (= X 0) (= Y 0))
      (COMMAND "REDRAW" "INSERT" "C:/ACAD/BLOCK/INT150-A" PAUSE  ))
      (IF (AND (= X 1) (= Y 0))
      (COMMAND "REDRAW" "INSERT" "C:/ACAD/BLOCK/INT150-B" PAUSE  ))
      (IF (AND (= X 2) (= Y 0))
      (COMMAND "REDRAW" "INSERT" "C:/ACAD/BLOCK/INT150-C" PAUSE  ))
      (IF (AND (= X 0) (= Y 1))
      (COMMAND "REDRAW" "INSERT" "C:/ACAD/BLOCK/INT100-A" PAUSE  ))
      (IF (AND (= X 1) (= Y 1))
      (COMMAND "REDRAW" "INSERT" "C:/ACAD/BLOCK/INT100-B" PAUSE  ))
      (IF (AND (= X 2) (= Y 1))
      (COMMAND "REDRAW" "INSERT" "C:/ACAD/BLOCK/INT100-C" PAUSE  ))
      (IF (AND (= X 0) (= Y 2))
      (COMMAND "REDRAW" "INSERT" "C:/ACAD/BLOCK/INT80-A" PAUSE  ))
      (IF (AND (= X 1) (= Y 2))
      (COMMAND "REDRAW" "INSERT" "C:/ACAD/BLOCK/INT80-B" PAUSE  ))
      (IF (AND (= X 2) (= Y 2))
      (COMMAND "REDRAW" "INSERT" "C:/ACAD/BLOCK/INT80-C" PAUSE  ))
      (IF (AND (= X 0) (= Y 3))
      (COMMAND "REDRAW" "INSERT" "C:/ACAD/BLOCK/INT50-A" PAUSE  ))
      (IF (AND (= X 1) (= Y 3))
      (COMMAND "REDRAW" "INSERT" "C:/ACAD/BLOCK/INT50-B" PAUSE  ))
      (IF (AND (= X 2) (= Y 3))
      (COMMAND "REDRAW" "INSERT" "C:/ACAD/BLOCK/INT50-C" PAUSE  ))
      )

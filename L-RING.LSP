(DEFUN C:L-RING ()
   (SETVAR "CMDECHO" 0)
   (SETQ VC (GETVAR "VIEWCTR"))
   (SETQ YR (GETVAR "VIEWSIZE"))
   (SETQ XR (* YR 1.3864))
   (SETQ YD (/ YR 8))
   (SETQ XD (/ XR 8))
   (SETQ XB (- (CAR VC) (/ XR 2)))
   (SETQ YB (- (CADR VC) (/ YR 2)))
   (COMMAND "VSLIDE" "C:/ACAD/SLIDE/L-RING")
;----
   (SETQ PT (GETPOINT "\nPLEASE DIGIT THE CHAR. TABLE : "))
             (SETQ XP (CAR PT))
             (SETQ YP (CADR PT))
             (SETQ XAA (- XP XB))
             (SETQ YAA (- YP YB))
             (SETQ XA (ABS XAA))
             (SETQ YA (ABS YAA))
             (SETQ X (FIX ( / XA XD)))
             (SETQ Y (FIX ( / YA YD)))
;
      (IF (AND (= X 1) (= Y 0))
      (COMMAND "REDRAW" "INSERT" "C:/ACAD/BLOCK/P22" PAUSE 1 1))
      (IF (AND (= X 3) (= Y 0))
      (COMMAND "REDRAW" "INSERT" "C:/ACAD/BLOCK/P22-1" PAUSE 1 1))
      (IF (AND (= X 5) (= Y 0))
      (COMMAND "REDRAW" "INSERT" "C:/ACAD/BLOCK/WG24" PAUSE 1 1))
      (IF (AND (= X 1) (= Y 1))
      (COMMAND "REDRAW" "INSERT" "C:/ACAD/BLOCK/P20" PAUSE 1 1))
      (IF (AND (= X 3) (= Y 1))
      (COMMAND "REDRAW" "INSERT" "C:/ACAD/BLOCK/P20-1" PAUSE 1 1))
      (IF (AND (= X 5) (= Y 1))
      (COMMAND "REDRAW" "INSERT" "C:/ACAD/BLOCK/WG22" PAUSE 1 1))
      (IF (AND (= X 1) (= Y 2))
      (COMMAND "REDRAW" "INSERT" "C:/ACAD/BLOCK/P18" PAUSE 1 1))
      (IF (AND (= X 3) (= Y 2))
      (COMMAND "REDRAW" "INSERT" "C:/ACAD/BLOCK/P18-1" PAUSE 1 1))
      (IF (AND (= X 5) (= Y 2))
      (COMMAND "REDRAW" "INSERT" "C:/ACAD/BLOCK/WG20" PAUSE 1 1))
      (IF (AND (= X 1) (= Y 3))
      (COMMAND "REDRAW" "INSERT" "C:/ACAD/BLOCK/P16" PAUSE 1 1))
      (IF (AND (= X 3) (= Y 3))
      (COMMAND "REDRAW" "INSERT" "C:/ACAD/BLOCK/P16-1" PAUSE 1 1))
      (IF (AND (= X 5) (= Y 3))
      (COMMAND "REDRAW" "INSERT" "C:/ACAD/BLOCK/WG18" PAUSE 1 1))
      (IF (AND (= X 1) (= Y 4))
      (COMMAND "REDRAW" "INSERT" "C:/ACAD/BLOCK/P14" PAUSE 1 1))
      (IF (AND (= X 3) (= Y 4))
      (COMMAND "REDRAW" "INSERT" "C:/ACAD/BLOCK/P14-1" PAUSE 1 1))
      (IF (AND (= X 5) (= Y 4))
      (COMMAND "REDRAW" "INSERT" "C:/ACAD/BLOCK/WG16" PAUSE 1 1))
      (IF (AND (= X 1) (= Y 5))
      (COMMAND "REDRAW" "INSERT" "C:/ACAD/BLOCK/P12" PAUSE 1 1))
      (IF (AND (= X 3) (= Y 5))
      (COMMAND "REDRAW" "INSERT" "C:/ACAD/BLOCK/P12-1" PAUSE 1 1))
      (IF (AND (= X 5) (= Y 5))
      (COMMAND "REDRAW" "INSERT" "C:/ACAD/BLOCK/WG14" PAUSE 1 1))
      (IF (AND (= X 1) (= Y 6))
      (COMMAND "REDRAW" "INSERT" "C:/ACAD/BLOCK/P10" PAUSE 1 1))
      (IF (AND (= X 3) (= Y 6))
      (COMMAND "REDRAW" "INSERT" "C:/ACAD/BLOCK/P10-1" PAUSE 1 1))
      (IF (AND (= X 5) (= Y 6))
      (COMMAND "REDRAW" "INSERT" "C:/ACAD/BLOCK/WG12" PAUSE 1 1))
      (IF (AND (= X 1) (= Y 7))
      (COMMAND "REDRAW" "INSERT" "C:/ACAD/BLOCK/P8" PAUSE 1 1))
      (IF (AND (= X 3) (= Y 7))
      (COMMAND "REDRAW" "INSERT" "C:/ACAD/BLOCK/P8-1" PAUSE 1 1))
      (IF (AND (= X 5) (= Y 7))
      (COMMAND "REDRAW" "INSERT" "C:/ACAD/BLOCK/WG10" PAUSE 1 1))
      )

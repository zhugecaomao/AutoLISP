DEFUN C:LCHG15
;SET LAYER
(COMMAND "SETVAR" "CMDECHO" 0)
;(IF (= (TYPE F1) 'FILE ) "YES"  (STOP))
;(IF (= (TYPE F2) 'FILE ) "YES" (STOP))
(setq SET15 (findfile "/ACAD/HON/SET/SET15.SET"))
(IF (= SET15 NIL)
    (PROGN
       (PROMPT "\nPLEASE SETTING LAYER:" )
       (SETQ FC (OPEN "/ACAD/HON/SET/SET15.SET" "w"))
       (setq SETL15 (GETSTRING T"\nSETTING LAYER ? <15>:"))
       (IF (OR (= SETL15 "") (= SETL15 NIL))
              (WRITE-LINE "15" FC)
              (WRITE-LINE SETL15 FC)
       )
       (CLOSE FC)
    )
)

(IF (/= SET15 NIL)
    (PROGN
       (SETQ FC (OPEN "/ACAD/HON/SET/SET15.SET" "r"))
       (SETQ SETL15 (READ-LINE FC))
       (IF (OR (= SETL15 "") (= SETL15 NIL))
           (CLOSE FC)
       )
       (IF (OR (= SETL15 "") (= SETL15 NIL))
           (PROGN
              (PROMPT "\nPLEASE SETTING LAYER:" )
              (SETQ FC (OPEN "/ACAD/HON/SET/SET15.SET" "w"))
              (setq SETL15 (GETSTRING T"\nSETTING LAYER ? <15>:"))
              (IF (= SETL15 "")
                  (WRITE-LINE "15" FC)
                  (WRITE-LINE SETL15 FC)
              )
           (CLOSE FC)
           )
       )
       (SETQ FC (OPEN "/ACAD/HON/SET/SET15.SET" "r"))
       (SETQ SETL15 (READ-LINE FC))
       (CLOSE FC)
       (PROMPT "\nLAYER NAME IS:" )(PROMPT SETL15)(TERPRI)
       (SETQ LR SETL15)
       (C:QCHNG)
    )
)

(defun C:MT()
;(setq da (getreal "\nEnter diameter of ball: "))
(setq da 12)
(setq p1 (getpoint "\nStart point: ")
      p2 (getpoint p1 "\nEnd point: "))
(setvar "cmdecho" 0)
(command "doughnut" 0 1 p1 "")
(command "line" p1 p2 "")
(setq cp (polar p2 0 (/ da 2)))
(command "circle" cp (/ da 2))
(setq tx (getstring T "\nKey in number: "))
(command "text" "m" cp (* 0.4 da) "" tx)
(setvar "cmdecho" 1)
)

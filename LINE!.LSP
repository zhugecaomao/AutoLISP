(defun C:li()
(setq p1 '(24.02 -34.98 5.83))
(setq p2 '(24.84 -34.98 8.45))
(setq p3 '(17.66 -34.98 10.99))
(setq p4 '(14.48 -34.98 13.26))
(setq p5 '(11.30 -34.98 15.20))
(setq p6 '(8.12 -34.98 16.87))
(setq p7 '(4.94 -34.98 18.30))
(setq p8 '(1.76 -34.98 19.54))
(setq p9 '(-1.41 -34.98 20.61))
(setq p10 '(-4.59 -34.98 21.55))

(setq p11 '(27.20 -38.16 1.73))
(setq p12 '(24.02 -38.16 4.43))
(setq p13 '(20.84 -38.16 7.16))
(setq p14 '(17.66 -38.16 9.71))
(setq p15 '(14.48 -38.16 11.95))
(setq p16 '(11.30 -38.16 13.90))
(setq p17 '(8.12 -38.16 15.61))
(setq p18 '(4.94 -38.16 17.10))
(setq p19 '(1.76 -38.16 18.39))
(setq p20 '(-1.41 -38.16 19.53))
(setq p21 '(-4.59 -38.16 20.54))
(setq p22 '(-7.77 -38.16 21.45))

(setq p23 '(27.20 -41.34 0.21))
(setq p24 '(24.02 -41.34 3.10))
(setq p25 '(20.84 -41.34 5.87))
(setq p26 '(17.66 -41.34 8.40))
(setq p27 '(14.48 -41.34 10.64))
(setq p28 '(11.30 -41.34 12.62))
(setq p29 '(8.12 -41.34 14.37))
(setq p30 '(4.94 -41.34 15.91))
(setq p31 '(1.76 -41.34 17.27))
(setq p32 '(-1.41 -41.34 18.47))
(setq p33 '(-4.59 -41.34 19.55))
(setq p34 '(-7.77 -41.34 20.54))

(setq p35 '(27.20 -44.52 -1.19))
(setq p36 '(24.02 -44.52 1.80))
(setq p37 '(20.84 -44.52 4.57))
(setq p38 '(17.66 -44.52 7.08))
(setq p39 '(14.48 -44.52 9.32))
(setq p40 '(11.30 -44.52 11.34))
(setq p41 '(8.12 -44.52 13.14))
(setq p42 '(4.94 -44.52 14.74))
(setq p43 '(1.76 -44.52 16.16))
(setq p44 '(-1.41 -44.52 17.44))
(setq p45 '(-4.59 -44.52 18.60))
(setq p46 '(-7.77 -44.52 19.66))
(setq p47 '(-10.95 -44.52 20.65))

(setq p48 '(30.38 -47.7 -5.86))
(setq p49 '(27.20 -47.7 -2.58))
(setq p50 '(24.02 -47.7 0.48))
(setq p51 '(20.84 -47.7 3.29))
(setq p52 '(17.66 -47.7 5.81))
(setq p53 '(14.48 -47.7 8.08))
(setq p54 '(11.30 -47.7 10.13))
(setq p55 '(8.12 -47.7 11.97))
(setq p56 '(4.94 -47.7 13.62))
(setq p57 '(1.76 -47.7 15.10))
(setq p58 '(-1.41 -47.7 16.44))
(setq p59 '(-4.59 -47.7 17.67))
(setq p60 '(-7.77 -47.7 18.80))
(setq p61 '(-10.95 -47.7 19.87))
(setq p62 '(-14.13 -47.7 20.89))

(setq p63 '(30.38 -50.88 -7.06))
(setq p64 '(27.20 -50.88 -3.81))
(setq p65 '(24.02 -50.88 -0.71))
(setq p66 '(20.84 -50.88 2.13))
(setq p67 '(17.66 -50.88 4.70))
(setq p68 '(14.48 -50.88 7.00))
(setq p69 '(11.30 -50.88 9.05))
(setq p70 '(8.12 -50.88 10.91))
(setq p71 '(4.94 -50.88 12.59))
(setq p72 '(1.76 -50.88 14.13))
(setq p73 '(-1.41 -50.88 15.53))
(setq p74 '(-4.59 -50.88 16.83))
(setq p75 '(-7.77 -50.88 18.03))
(setq p76 '(-10.95 -50.88 19.16))
(setq p77 '(-14.13 -50.88 20.23))
(setq p78 '(-17.31 -50.88 21.25))

(setq p79 '(30.38 -54.06 -8.20))
(setq p80 '(27.20 -54.06 -4.93))
(setq p81 '(24.02 -54.06 -1.84))
(setq p82 '(20.84 -54.06 0.98))
(setq p83 '(17.66 -54.06 3.54))
(setq p84 '(14.48 -54.06 5.87))
(setq p85 '(11.30 -54.06 7.99))
(setq p86 '(8.12 -54.06 9.93))
(setq p87 '(4.94 -54.06 11.69))
(setq p88 '(1.76 -54.06 13.31))
(setq p89 '(-1.41 -54.06 14.79))
(setq p90 '(-4.59 -54.06 16.16))
(setq p91 '(-7.77 -54.06 17.44))
(setq p92 '(-10.95 -54.06 18.65))
(setq p93 '(-14.13 -54.06 19.80))
(setq p94 '(-17.31 -54.06 20.92))
(setq p95 '(-20.49 -54.06 22.01))

(setq p96 '(30.38 -57.24 -9.32))
(setq p97 '(27.20 -57.24 -6.02))
(setq p98 '(24.02 -57.24 -2.91))
(setq p99 '(20.84 -57.24 -0.04))
(setq p100 '(17.66 -57.24 2.55))
(setq p101 '(14.48 -57.24 4.91))
(setq p102 '(11.30 -57.24 7.07))
(setq p103 '(8.12 -57.24 9.05))
(setq p104 '(4.94 -57.24 10.87))
(setq p105 '(1.76 -57.24 12.54))
(setq p106 '(-1.41 -57.24 14.09))
(setq p107 '(-4.59 -57.24 15.53))
(setq p108 '(-7.77 -57.24 16.89))
(setq p109 '(-10.95 -57.24 18.17))
(setq p110 '(-14.13 -57.24 19.41))
(setq p111 '(-17.31 -57.24 20.60))
(setq p112 '(-20.49 -57.24 21.77))

(setq p113 '(33.56 -60.42 -13.75))
(setq p114 '(30.38 -60.42 -10.37))
(setq p115 '(27.20 -60.42 -7.06))
(setq p116 '(24.02 -60.42 -3.92))
(setq p117 '(20.84 -60.42 -1.04))
(setq p118 '(17.66 -60.42 1.58))
(setq p119 '(14.48 -60.42 3.99))
(setq p120 '(11.30 -60.42 6.20))
(setq p121 '(8.12 -60.42 8.24))
(setq p122 '(4.94 -60.42 10.12))
(setq p123 '(1.76 -60.42 11.86))
(setq p124 '(-1.41 -60.42 13.48))
(setq p125 '(-4.59 -60.42 14.99))
(setq p126 '(-7.77 -60.42 16.42))
(setq p127 '(-10.95 -60.42 17.78))
(setq p128 '(-14.13 -60.42 19.09))
(setq p129 '(-17.31 -60.42 20.35))
(setq p130 '(-20.49 -60.42 21.59))
(setq p131 '(-23.68 -60.42 22.81))
(setq p132 '(-26.85 -60.42 24.03))

(setq p133 '(33.56 -63.6 -14.71))
(setq p134 '(30.38 -63.6 -11.30))
(setq p135 '(27.20 -63.6 -7.97))
(setq p136 '(24.02 -63.6 -4.81))
(setq p137 '(20.84 -63.6 -1.88))
(setq p138 '(17.66 -63.6 0.78))
(setq p139 '(14.48 -63.6 3.22))
(setq p140 '(11.30 -63.6 5.45))
(setq p141 '(8.12 -63.6 7.52))
(setq p142 '(4.94 -63.6 9.44))
(setq p143 '(1.76 -63.6 11.23))
(setq p144 '(-1.41 -63.6 12.90))
(setq p145 '(-4.59 -63.6 14.40))
(setq p146 '(-7.77 -63.6 15.98))
(setq p147 '(-10.95 -63.6 17.41))
(setq p148 '(-14.13 -63.6 18.79))
(setq p149 '(-17.31 -63.6 20.13))
(setq p150 '(-20.49 -63.6 21.44))
(setq p151 '(-23.67 -63.6 22.74))
(setq p152 '(-26.85 -63.6 24.02))
(setq p153 '(-30.03 -63.6 25.30))

(setq p154 '(33.56 -66.78 -15.63))
(setq p155 '(30.38 -66.78 -12.17))
(setq p156 '(27.20 -66.78 -8.83))
(setq p157 '(24.02 -66.78 -5.65))
(setq p158 '(20.84 -66.78 -2.71))
(setq p159 '(17.66 -66.78 0.00))
(setq p160 '(14.48 -66.78 2.48))
(setq p161 '(11.30 -66.78 4.75))
(setq p162 '(8.12 -66.78 6.86))
(setq p163 '(4.94 -66.78 8.83))
(setq p164 '(1.76 -66.78 10.67))
(setq p165 '(-1.41 -66.78 12.41))
(setq p166 '(-4.59 -66.78 14.06))
(setq p167 '(-7.77 -66.78 15.62))
(setq p168 '(-10.95 -66.78 17.12))
(setq p169 '(-14.13 -66.78 18.57))
(setq p170 '(-17.31 -66.78 19.98))
(setq p171 '(-20.49 -66.78 21.35))
(setq p172 '(-23.67 -66.78 22.70))
(setq p173 '(-26.85 -66.78 24.03))
(setq p174 '(-30.03 -66.78 25.37))
(setq p175 '(-33.21 -66.78 26.71))

(setq p176 '(33.56 -69.96 -16.35))
(setq p177 '(30.38 -69.96 -12.92))
(setq p178 '(27.20 -69.96 -9.59))
(setq p179 '(24.02 -69.96 -6.43))
(setq p180 '(20.84 -69.96 -3.47))
(setq p181 '(17.66 -69.96 -0.74))
(setq p182 '(14.48 -69.96 1.76))
(setq p183 '(11.30 -69.96 4.08))
(setq p184 '(8.12 -69.96 6.24))
(setq p185 '(4.94 -69.96 8.26))
(setq p186 '(1.76 -69.96 10.16))
(setq p187 '(-1.41 -69.96 11.96))
(setq p188 '(-4.59 -69.96 13.66))
(setq p189 '(-7.77 -69.96 15.28))
(setq p190 '(-10.95 -69.96 16.84))
(setq p191 '(-14.13 -69.96 18.34))
(setq p192 '(-17.31 -69.96 19.80))
(setq p193 '(-20.49 -69.96 21.23))
(setq p194 '(-23.67 -69.96 22.64))
(setq p195 '(-26.85 -69.96 24.04))
(setq p196 '(-30.03 -69.96 25.44))
(setq p197 '(-33.21 -69.96 26.85))
(setq p198 '(-36.39 -69.96 28.27))

(setq p199 '(33.56 -73.14 -17.02))
(setq p200 '(30.38 -73.14 -13.62))
(setq p201 '(27.20 -73.14 -10.34))
(setq p202 '(24.02 -73.14 -7.20))
(setq p203 '(20.84 -73.14 -4.32))
(setq p204 '(17.86 -73.14 -1.45))
(setq p205 '(14.48 -73.14 1.12))
(setq p206 '(11.30 -73.14 3.50))
(setq p207 '(8.12 -73.14 5.71))
(setq p208 '(4.94 -73.14 7.77))
(setq p209 '(1.76 -73.14 9.72))
(setq p210 '(-1.41 -73.14 11.56))
(setq p211 '(-4.59 -73.14 13.31))
(setq p212 '(-7.77 -73.14 14.99))
(setq p213 '(-10.95 -73.14 16.60))
(setq p214 '(-14.13 -73.14 18.16))
(setq p215 '(-17.31 -73.14 19.68))
(setq p216 '(-20.49 -73.14 21.17))
(setq p217 '(-23.67 -73.14 22.63))
(setq p218 '(-26.85 -73.14 24.09))
(setq p219 '(-30.04 -73.14 25.53))
(setq p220 '(-33.21 -73.14 26.98))
(setq p221 '(-36.39 -73.14 28.44))
(setq p222 '(-39.57 -73.14 29.90))

(setq p223 '(33.56 -76.32 -17.55))
(setq p224 '(30.38 -76.32 -14.20))
(setq p225 '(27.20 -76.32 -10.94))
(setq p226 '(24.02 -76.32 -7.80))
(setq p227 '(20.84 -76.32 -4.83))
(setq p228 '(17.66 -76.32 -2.05))
(setq p229 '(14.48 -76.32 0.52))
(setq p230 '(11.30 -76.32 2.92))
(setq p231 '(8.12 -76.32 5.16))
(setq p232 '(4.94 -76.32 7.27))
(setq p233 '(1.76 -76.32 9.27))
(setq p234 '(-1.41 -76.32 11.16))
(setq p235 '(-4.59 -76.32 12.98))
(setq p236 '(-7.77 -76.32 14.71))
(setq p237 '(-10.95 -76.32 16.39))
(setq p238 '(-14.13 -76.32 18.01))
(setq p239 '(-17.31 -76.32 19.58))
(setq p240 '(-20.49 -76.32 21.13))
(setq p241 '(-23.67 -76.32 22.64))
(setq p242 '(-26.85 -76.32 24.13))
(setq p243 '(-30.04 -76.32 25.62))
(setq p244 '(-33.21 -76.32 27.10))
(setq p245 '(-36.39 -76.32 28.58))
(setq p246 '(-39.57 -76.32 30.07))
(setq p247 '(-42.75 -76.32 31.56))
(setq p248 '(-45.93 -76.32 33.06))

(setq p249 '(33.56 -79.5 -18.21))
(setq p250 '(30.38 -79.5 -14.80))
(setq p251 '(27.20 -79.5 -11.51))
(setq p252 '(24.02 -79.5 -8.38))
(setq p253 '(20.84 -79.5 -5.43))
(setq p254 '(17.66 -79.5 -2.67))
(setq p255 '(14.48 -79.5 -0.09))
(setq p256 '(11.30 -79.5 2.33))
(setq p257 '(8.12 -79.5 4.63))
(setq p258 '(4.94 -79.5 6.80))
(setq p259 '(1.76 -79.5 8.86))
(setq p260 '(-1.41 -79.5 10.82))
(setq p261 '(-4.59 -79.5 12.69))
(setq p262 '(-7.77 -79.5 14.48))
(setq p263 '(-10.95 -79.5 16.21))
(setq p264 '(-14.13 -79.5 17.88))
(setq p265 '(-17.31 -79.5 19.50))
(setq p266 '(-20.49 -79.5 21.08))
(setq p267 '(-23.68 -79.5 22.64))
(setq p268 '(-26.85 -79.5 24.17))
(setq p269 '(-30.04 -79.5 25.69))
(setq p270 '(-33.21 -79.5 27.20))
(setq p271 '(-36.39 -79.5 28.71))
(setq p272 '(-39.57 -79.5 30.22))
(setq p273 '(-42.75 -79.5 31.73))
(setq p274 '(-45.93 -79.5 33.24))
(setq p275 '(-49.11 -79.5 34.75))
(setq p276 '(-52.29 -79.5 36.27))

(setq p277 '(33.56 -82.68 -18.65))
(setq p278 '(30.38 -82.68 -15.31))
(setq p279 '(27.20 -82.68 -12.06))
(setq p280 '(24.02 -82.68 -8.95))
(setq p281 '(20.84 -82.68 -5.99))
(setq p282 '(17.66 -82.68 -3.21))
(setq p283 '(14.48 -82.68 -0.60))
(setq p284 '(11.30 -82.68 1.85))
(setq p285 '(8.12 -82.68 4.18))
(setq p286 '(4.94 -82.68 6.39))
(setq p287 '(1.76 -82.68 8.49))
(setq p288 '(-1.41 -82.68 10.49))
(setq p289 '(-4.59 -82.68 12.41))
(setq p290 '(-7.77 -82.68 14.25))
(setq p291 '(-10.95 -82.68 16.01))
(setq p292 '(-14.13 -82.68 17.73))
(setq p293 '(-17.31 -82.68 19.39))
(setq p294 '(-20.49 -82.68 21.02))
(setq p295 '(-23.67 -82.68 22.61))
(setq p296 '(-26.85 -82.68 24.18))
(setq p297 '(-30.04 -82.68 25.74))
(setq p298 '(-33.21 -82.68 27.28))
(setq p299 '(-36.39 -82.68 28.82))
(setq p300 '(-39.57 -82.68 30.35))
(setq p301 '(-42.75 -82.68 31.87))
(setq p302 '(-45.93 -82.68 33.39))
(setq p303 '(-49.11 -82.68 34.89))
(setq p304 '(-52.29 -82.68 36.40))
(setq p305 '(-55.47 -82.68 37.89))
(setq p306 '(-58.65 -82.68 39.38))

(setq p307 '(33.56 -85.86 -19.30))
(setq p308 '(30.38 -85.86 -15.91))
(setq p309 '(27.20 -85.86 -12.62))
(setq p310 '(24.02 -85.86 -9.48))
(setq p311 '(20.84 -85.86 -6.50))
(setq p312 '(17.66 -85.86 -3.70))
(setq p313 '(14.48 -85.86 -1.07))
(setq p314 '(11.30 -85.86 1.41))
(setq p315 '(8.12 -85.86 3.77))
(setq p316 '(4.94 -85.86 6.01))
(setq p317 '(1.76 -85.86 8.14))
(setq p318 '(-1.41 -85.86 10.18))
(setq p319 '(-4.59 -85.86 12.14))
(setq p320 '(-7.77 -85.86 14.02))
(setq p321 '(-10.95 -85.86 15.83))
(setq p322 '(-14.13 -85.86 17.58))
(setq p323 '(-17.31 -85.86 19.29))
(setq p324 '(-20.49 -85.86 20.95))
(setq p325 '(-23.68 -85.86 22.58))
(setq p326 '(-26.85 -85.86 24.18))
(setq p327 '(-30.04 -85.86 25.76))
(setq p328 '(-33.21 -85.86 27.32))
(setq p329 '(-36.39 -85.86 28.87))
(setq p330 '(-39.57 -85.86 30.41))
(setq p331 '(-42.75 -85.86 31.94))
(setq p332 '(-45.93 -85.86 33.46))
(setq p333 '(-49.11 -85.86 34.97))
(setq p334 '(-52.29 -85.86 36.48))
(setq p335 '(-55.47 -85.86 37.97))
(setq p336 '(-58.65 -85.86 39.45))
(setq p337 '(-61.83 -85.86 40.91))

(setq p338 '(33.56 -89.04 -19.69))
(setq p339 '(30.38 -89.04 -16.33))
(setq p340 '(27.20 -89.04 -13.08))
(setq p341 '(24.02 -89.04 -9.95))
(setq p342 '(20.84 -89.04 -6.98))
(setq p343 '(17.66 -89.04 -4.18))
(setq p344 '(14.48 -89.04 -1.53))
(setq p345 '(11.30 -89.04 0.97))
(setq p346 '(8.12 -89.04 3.35))
(setq p347 '(4.94 -89.04 5.63))
(setq p348 '(1.76 -89.04 7.80))
(setq p349 '(-1.41 -89.04 9.88))
(setq p350 '(-4.59 -89.04 11.88))
(setq p351 '(-7.77 -89.04 13.79))
(setq p352 '(-10.95 -89.04 15.64))
(setq p353 '(-14.13 -89.04 17.43))
(setq p354 '(-17.31 -89.04 19.17))
(setq p355 '(-20.49 -89.04 20.87))
(setq p356 '(-23.68 -89.04 22.53))
(setq p357 '(-26.85 -89.04 24.15))
(setq p358 '(-30.04 -89.04 25.76))
(setq p359 '(-33.21 -89.04 27.34))
(setq p360 '(-36.39 -89.04 28.91))
(setq p361 '(-39.57 -89.04 30.46))
(setq p362 '(-42.75 -89.04 32.00))
(setq p363 '(-45.93 -89.04 33.52))
(setq p364 '(-49.11 -89.04 35.03))
(setq p365 '(-52.29 -89.04 36.52))
(setq p366 '(-55.47 -89.04 37.99))
(setq p367 '(-58.65 -89.04 39.44))
(setq p368 '(-61.83 -89.04 40.86))
(setq p369 '(-65.01 -89.04 42.26))

(setq p370 '(33.56 -92.22 -20.13))
(setq p371 '(30.38 -92.22 -16.78))
(setq p372 '(27.20 -92.22 -13.54))
(setq p373 '(24.02 -92.22 -10.41))
(setq p374 '(20.84 -92.22 -7.44))
(setq p375 '(17.66 -92.22 -4.63))
(setq p376 '(14.48 -92.22 -1.96))
(setq p377 '(11.30 -92.22 0.56))
(setq p378 '(8.12 -92.22 2.98))
(setq p379 '(4.94 -92.22 5.28))
(setq p380 '(1.76 -92.22 7.49))
(setq p381 '(-1.41 -92.22 9.60))
(setq p382 '(-4.59 -92.22 11.63))
(setq p383 '(-7.77 -92.22 13.59))
(setq p384 '(-10.95 -92.22 15.48))
(setq p385 '(-14.13 -92.22 17.30))
(setq p386 '(-17.31 -92.22 19.08))
(setq p387 '(-20.49 -92.22 20.81))
(setq p388 '(-23.68 -92.22 22.50))
(setq p389 '(-26.85 -92.22 24.15))
(setq p390 '(-30.04 -92.22 25.78))
(setq p391 '(-33.21 -92.22 27.38))
(setq p392 '(-36.39 -92.22 28.96))
(setq p393 '(-39.57 -92.22 30.52))
(setq p394 '(-42.75 -92.22 32.06))
(setq p395 '(-45.93 -92.22 33.59))
(setq p396 '(-49.11 -92.22 35.11))
(setq p397 '(-52.29 -92.22 36.59))
(setq p398 '(-55.47 -92.22 38.05))
(setq p399 '(-58.65 -92.22 39.47))
(setq p400 '(-61.83 -92.22 40.85))
(setq p401 '(-65.01 -92.22 42.20))
(setq p402 '(-68.19 -92.22 43.54))

(setq p403 '(33.56 -95.4 -20.31))
(setq p404 '(30.38 -95.4 -17.07))
(setq p405 '(27.20 -95.4 -13.91))
(setq p406 '(24.02 -95.4 -10.86))
(setq p407 '(20.84 -95.4 -7.92))
(setq p408 '(17.66 -95.4 -5.12))
(setq p409 '(14.48 -95.4 -2.45))
(setq p410 '(11.30 -95.4 0.10))
(setq p411 '(8.12 -95.4 2.54))
(setq p412 '(4.94 -95.4 4.89))
(setq p413 '(1.76 -95.4 7.13))
(setq p414 '(-1.41 -95.4 9.29))
(setq p415 '(-4.59 -95.4 11.35))
(setq p416 '(-7.77 -95.4 13.34))
(setq p417 '(-10.95 -95.4 15.26))
(setq p418 '(-14.13 -95.4 17.11))
(setq p419 '(-17.31 -95.4 18.91))
(setq p420 '(-20.49 -95.4 20.66))
(setq p421 '(-23.68 -95.4 22.37))
(setq p422 '(-26.85 -95.4 24.04))
(setq p423 '(-30.04 -95.4 25.68))
(setq p424 '(-33.21 -95.4 27.29))
(setq p425 '(-36.39 -95.4 28.88))
(setq p426 '(-39.57 -95.4 30.45))
(setq p427 '(-42.75 -95.4 31.99))
(setq p428 '(-45.93 -95.4 33.51))
(setq p429 '(-49.11 -95.4 35.00))
(setq p430 '(-52.29 -95.4 36.46))
(setq p431 '(-55.47 -95.4 37.90))
(setq p432 '(-58.65 -95.4 39.29))
(setq p433 '(-61.83 -95.4 40.65))
(setq p434 '(-65.01 -95.4 41.98))
(setq p435 '(-68.19 -95.4 43.30))

(setq p436 '(33.56 -98.58 -20.74))
(setq p437 '(30.38 -98.58 -17.50))
(setq p438 '(27.20 -98.58 -14.34))
(setq p439 '(24.02 -98.58 -11.28))
(setq p440 '(20.84 -98.58 -8.34))
(setq p441 '(17.66 -98.58 -5.54))
(setq p442 '(14.48 -98.58 -2.85))
(setq p443 '(11.30 -98.58 -0.28))
(setq p444 '(8.12 -98.58 2.17))
(setq p445 '(4.94 -98.58 4.53))
(setq p446 '(1.76 -98.58 6.79))
(setq p447 '(-1.41 -98.58 8.96))
(setq p448 '(-4.59 -98.58 11.05))
(setq p449 '(-7.77 -98.58 13.06))
(setq p450 '(-10.95 -98.58 15.00))
(setq p451 '(-14.13 -98.58 16.88))
(setq p452 '(-17.31 -98.58 18.70))
(setq p453 '(-20.49 -98.58 20.47))
(setq p454 '(-23.68 -98.58 22.20))
(setq p455 '(-26.85 -98.58 23.88))
(setq p456 '(-30.04 -98.58 25.54))
(setq p457 '(-33.21 -98.58 27.16))
(setq p458 '(-36.39 -98.58 28.75))
(setq p459 '(-39.57 -98.58 30.31))
(setq p460 '(-42.75 -98.58 31.85))
(setq p461 '(-45.93 -98.58 33.37))
(setq p462 '(-49.11 -98.58 34.86))
(setq p463 '(-52.29 -98.58 36.31))
(setq p464 '(-55.47 -98.58 37.72))
(setq p465 '(-58.65 -98.58 39.08))
(setq p466 '(-61.83 -98.58 40.39))
(setq p467 '(-65.01 -98.58 41.67))
(setq p468 '(-68.19 -98.58 42.91))

(setq p469 '(33.56 -101.76 -20.98))
(setq p470 '(30.38 -101.76 -17.81))
(setq p471 '(27.20 -101.76 -14.70))
(setq p472 '(24.02 -101.76 -11.68))
(setq p473 '(20.84 -101.76 -8.77))
(setq p474 '(17.66 -101.76 -5.98))
(setq p475 '(14.48 -101.76 -3.29))
(setq p476 '(11.30 -101.76 -0.72))
(setq p477 '(8.12 -101.76 1.75))
(setq p478 '(4.94 -101.76 4.13))
(setq p479 '(1.76 -101.76 6.42))
(setq p480 '(-1.41 -101.76 8.62))
(setq p481 '(-4.59 -101.76 10.73))
(setq p482 '(-7.77 -101.76 12.77))
(setq p483 '(-10.95 -101.76 14.73))
(setq p484 '(-14.13 -101.76 16.63))
(setq p485 '(-17.31 -101.76 18.46))
(setq p486 '(-20.49 -101.76 20.25))
(setq p487 '(-23.68 -101.76 21.99))
(setq p488 '(-26.85 -101.76 23.69))
(setq p489 '(-30.04 -101.76 25.34))
(setq p490 '(-33.21 -101.76 26.97))
(setq p491 '(-36.39 -101.76 28.56))
(setq p492 '(-39.57 -101.76 30.13))
(setq p493 '(-42.75 -101.76 31.66))
(setq p494 '(-45.93 -101.76 33.17))
(setq p495 '(-49.11 -101.76 34.64))
(setq p496 '(-52.29 -101.76 36.07))
(setq p497 '(-55.47 -101.76 37.46))
(setq p498 '(-58.65 -101.76 38.81))
(setq p499 '(-61.83 -101.76 40.10))
(setq p500 '(-65.01 -101.76 41.35))
(setq p501 '(-68.19 -101.76 42.57))

(setq p502 '(30.38 -104.94 -18.10))
(setq p503 '(27.20 -104.94 -15.06))
(setq p504 '(24.02 -104.94 -12.08))
(setq p505 '(20.84 -104.94 -9.19))
(setq p506 '(17.66 -104.94 -6.40))
(setq p507 '(14.48 -104.94 -3.71))
(setq p508 '(11.30 -104.94 -1.13))
(setq p509 '(8.12 -104.94 1.35))
(setq p510 '(4.94 -104.94 3.74))
(setq p511 '(1.76 -104.94 6.04))
(setq p512 '(-1.41 -104.94 8.26))
(setq p513 '(-4.59 -104.94 10.39))
(setq p514 '(-7.77 -104.94 12.44))
(setq p515 '(-10.95 -104.94 14.42))
(setq p516 '(-14.13 -104.94 16.33))
(setq p517 '(-17.31 -104.94 18.18))
(setq p518 '(-20.49 -104.94 19.98))
(setq p519 '(-23.68 -104.94 21.73))
(setq p520 '(-26.85 -104.94 23.44))
(setq p521 '(-30.04 -104.94 25.10))
(setq p522 '(-33.21 -104.94 26.73))
(setq p523 '(-36.39 -104.94 28.32))
(setq p524 '(-39.57 -104.94 29.88))
(setq p525 '(-42.75 -104.94 31.40))
(setq p526 '(-45.93 -104.94 32.89))
(setq p527 '(-49.11 -104.94 34.35))
(setq p528 '(-52.29 -104.94 35.76))
(setq p529 '(-55.47 -104.94 37.14))
(setq p530 '(-58.65 -104.94 38.48))
(setq p531 '(-61.83 -104.94 39.78))
(setq p532 '(-65.01 -104.94 41.05))
(setq p533 '(-68.19 -104.94 42.29))

(setq p534 '(30.38 -108.12 -18.58))
(setq p535 '(27.20 -108.12 -15.54))
(setq p536 '(24.02 -108.12 -12.54))
(setq p537 '(20.84 -108.12 -9.63))
(setq p538 '(17.66 -108.12 -6.80))
(setq p539 '(14.48 -108.12 -4.08))
(setq p540 '(11.30 -108.12 -1.47))
(setq p541 '(8.12 -108.12 1.01))
(setq p542 '(4.94 -108.12 3.40))
(setq p543 '(1.76 -108.12 5.68))
(setq p544 '(-1.41 -108.12 7.88))
(setq p545 '(-4.59 -108.12 10.00))
(setq p546 '(-7.77 -108.12 12.04))
(setq p547 '(-10.95 -108.12 14.02))
(setq p548 '(-14.13 -108.12 15.95))
(setq p549 '(-17.31 -108.12 17.82))
(setq p550 '(-20.49 -108.12 19.64))
(setq p551 '(-23.68 -108.12 21.41))
(setq p552 '(-26.85 -108.12 23.13))
(setq p553 '(-30.04 -108.12 24.81))
(setq p554 '(-33.21 -108.12 26.44))
(setq p555 '(-36.39 -108.12 28.03))
(setq p556 '(-39.57 -108.12 29.57))
(setq p557 '(-42.75 -108.12 31.08))
(setq p558 '(-45.93 -108.12 32.54))
(setq p559 '(-49.11 -108.12 33.97))
(setq p560 '(-52.29 -108.12 35.37))
(setq p561 '(-55.47 -108.12 36.74))
(setq p562 '(-58.65 -108.12 38.10))
(setq p563 '(-61.83 -108.12 39.44))
(setq p564 '(-65.01 -108.12 40.78))
(setq p565 '(-68.19 -108.12 42.11))

(setq p566 '(30.38 -111.3 -18.97))
(setq p567 '(27.20 -111.3 -15.94))
(setq p568 '(24.02 -111.3 -12.97))
(setq p569 '(20.84 -111.3 -10.07))
(setq p570 '(17.66 -111.3 -7.25))
(setq p571 '(14.48 -111.3 -4.53))
(setq p572 '(11.30 -111.3 -1.92))
(setq p573 '(8.12 -111.3 0.57))
(setq p574 '(4.94 -111.3 2.96))
(setq p575 '(1.76 -111.3 5.25))
(setq p576 '(-1.41 -111.3 7.46))
(setq p577 '(-4.59 -111.3 9.58))
(setq p578 '(-7.77 -111.3 11.64))
(setq p579 '(-10.95 -111.3 13.63))
(setq p580 '(-14.13 -111.3 15.56))
(setq p581 '(-17.31 -111.3 17.44))
(setq p582 '(-20.49 -111.3 19.27))
(setq p583 '(-23.68 -111.3 21.05))
(setq p584 '(-26.85 -111.3 22.77))
(setq p585 '(-30.04 -111.3 24.46))
(setq p586 '(-33.21 -111.3 26.09))
(setq p587 '(-36.39 -111.3 27.68))
(setq p588 '(-39.57 -111.3 29.22))
(setq p589 '(-42.75 -111.3 30.71))
(setq p590 '(-45.93 -111.3 32.16))
(setq p591 '(-49.11 -111.3 33.57))
(setq p592 '(-52.29 -111.3 34.94))
(setq p593 '(-55.47 -111.3 36.28))
(setq p594 '(-58.65 -111.3 37.60))
(setq p595 '(-61.83 -111.3 38.89))
(setq p596 '(-65.01 -111.3 40.18))

(setq p597 '(30.38 -114.48 -19.25))
(setq p598 '(27.20 -114.48 -16.28))
(setq p599 '(24.02 -114.48 -13.35))
(setq p600 '(20.84 -114.48 -10.48))
(setq p601 '(17.66 -114.48 -7.69))
(setq p602 '(14.48 -114.48 -4.98))
(setq p603 '(11.30 -114.48 -2.38))
(setq p604 '(8.12 -114.48 0.11))
(setq p605 '(4.94 -114.48 2.51))
(setq p606 '(1.76 -114.48 4.81))
(setq p607 '(-1.41 -114.48 7.02))
(setq p608 '(-4.59 -114.48 9.15))
(setq p609 '(-7.77 -114.48 11.20))
(setq p610 '(-10.95 -114.48 13.20))
(setq p611 '(-14.13 -114.48 15.13))
(setq p612 '(-17.31 -114.48 17.01))
(setq p613 '(-20.49 -114.48 18.83))
(setq p614 '(-23.68 -114.48 20.61))
(setq p615 '(-26.85 -114.48 22.34))
(setq p616 '(-30.04 -114.48 24.02))
(setq p617 '(-33.21 -114.48 25.65))
(setq p618 '(-36.39 -114.48 27.24))
(setq p619 '(-39.57 -114.48 28.79))
(setq p620 '(-42.75 -114.48 30.30))
(setq p621 '(-45.93 -114.48 31.76))
(setq p622 '(-49.11 -114.48 33.18))
(setq p623 '(-52.29 -114.48 34.58))
(setq p624 '(-55.47 -114.48 35.95))
(setq p625 '(-58.65 -114.48 37.29))
(setq p626 '(-61.83 -114.48 38.62))

(setq p627 '(30.38 -117.66 -19.67))
(setq p628 '(27.20 -117.66 -16.71))
(setq p629 '(24.02 -117.66 -13.80))
(setq p630 '(20.84 -117.66 -10.94))
(setq p631 '(17.66 -117.66 -8.15))
(setq p632 '(14.48 -117.66 -5.45))
(setq p633 '(11.30 -117.66 -2.85))
(setq p634 '(8.12 -117.66 -0.35))
(setq p635 '(4.94 -117.66 2.03))
(setq p636 '(1.76 -117.66 4.33))
(setq p637 '(-1.41 -117.66 6.54))
(setq p638 '(-4.59 -117.66 8.68))
(setq p639 '(-7.77 -117.66 10.74))
(setq p640 '(-10.95 -117.66 12.74))
(setq p641 '(-14.13 -117.66 14.68))
(setq p642 '(-17.31 -117.66 16.57))
(setq p643 '(-20.49 -117.66 18.40))
(setq p644 '(-23.68 -117.66 20.19))
(setq p645 '(-26.85 -117.66 21.92))
(setq p646 '(-30.04 -117.66 23.60))
(setq p647 '(-33.21 -117.66 25.23))
(setq p648 '(-36.39 -117.66 26.80))
(setq p649 '(-39.57 -117.66 28.33))
(setq p650 '(-42.75 -117.66 29.83))
(setq p651 '(-45.93 -117.66 31.30))
(setq p652 '(-49.11 -117.66 32.74))
(setq p653 '(-52.29 -117.66 34.16))
(setq p654 '(-55.47 -117.66 35.57))

(setq p655 '(27.20 -120.84 -17.36))
(setq p656 '(24.02 -120.84 -14.41))
(setq p657 '(20.84 -120.84 -11.53))
(setq p658 '(17.66 -120.84 -8.72))
(setq p659 '(14.48 -120.84 -6.00))
(setq p660 '(11.30 -120.84 -3.38))
(setq p661 '(8.12 -120.84 -0.87))
(setq p662 '(4.94 -120.84 1.53))
(setq p663 '(1.76 -120.84 3.84))
(setq p664 '(-1.41 -120.84 6.06))
(setq p665 '(-4.59 -120.84 8.20))
(setq p666 '(-7.77 -120.84 10.27))
(setq p667 '(-10.95 -120.84 12.27))
(setq p668 '(-14.13 -120.84 14.21))
(setq p669 '(-17.31 -120.84 16.09))
(setq p670 '(-20.49 -120.84 17.93))
(setq p671 '(-23.68 -120.84 19.71))
(setq p672 '(-26.85 -120.84 21.45))
(setq p673 '(-30.04 -120.84 23.13))
(setq p674 '(-33.21 -120.84 24.76))
(setq p675 '(-36.39 -120.84 26.33))
(setq p676 '(-39.57 -120.84 27.87))
(setq p677 '(-42.75 -120.84 29.38))
(setq p678 '(-45.93 -120.84 30.87))
(setq p679 '(-49.11 -120.84 32.34))

(setq p680 '(24.02 -124.02 -14.62))
(setq p681 '(20.84 -124.02 -11.85))
(setq p682 '(17.66 -124.02 -9.13))
(setq p683 '(14.48 -124.02 -6.49))
(setq p684 '(11.30 -124.02 -3.92))
(setq p685 '(8.12 -124.02 -1.43))
(setq p686 '(4.94 -124.02 0.96))
(setq p687 '(1.76 -124.02 3.29))
(setq p688 '(-1.41 -124.02 5.53))
(setq p689 '(-4.59 -124.02 7.68))
(setq p690 '(-7.77 -124.02 9.74))
(setq p691 '(-10.95 -124.02 11.73))
(setq p692 '(-14.13 -124.02 13.65))
(setq p693 '(-17.31 -124.02 15.52))
(setq p694 '(-20.49 -124.02 17.33))
(setq p695 '(-23.68 -124.02 19.11))
(setq p696 '(-26.85 -124.02 20.86))
(setq p697 '(-30.04 -124.02 22.58))
(setq p698 '(-33.21 -124.02 24.28))
(setq p699 '(-36.39 -124.02 25.97))
(setq p700 '(-39.57 -124.02 27.65))

(setq p701 '(20.84 -127.2 -12.20))
(setq p702 '(17.66 -127.2 -9.54))
(setq p703 '(14.48 -127.2 -6.92))
(setq p704 '(11.30 -127.2 -4.37))
(setq p705 '(8.12 -127.2 -1.90))
(setq p706 '(4.94 -127.2 0.48))
(setq p707 '(1.76 -127.2 2.80))
(setq p708 '(-1.41 -127.2 5.04))
(setq p709 '(-4.59 -127.2 7.21))
(setq p710 '(-7.77 -127.2 9.30))
(setq p711 '(-10.95 -127.2 11.32))
(setq p712 '(-14.13 -127.2 13.25))
(setq p713 '(-17.31 -127.2 15.11))
(setq p714 '(-20.49 -127.2 16.88))
(setq p715 '(-23.68 -127.2 18.59))
(setq p716 '(-26.85 -127.2 20.26))

    (command "line" p1 p2 p3 p4 p5 p6 p7 p8 p9 p10 "")
    (command "line" p11 p12 p13 p14 p15 p16 p17 p18 p19 p20 p21 p22 "")
    (command "line" p23 p24 p25 p26 p27 p28 p29 p30 p31 p32 p33 p34 "")
    (command "line" p35 p36 p37 p38 p39 p40 p41 p42 p43 "")
    (command "line" p43 p44 p45 p46 p47 "")
    (command "line" p48 p49 p50 p51 p52 p53 "")
    (command "line" p53 p54 p55 p56 p57 p58 p59 p60 p61 p62 "")
    (command "line" p63 p64 p65 p66 p67 p68 p69 p70 p71 p72 p73 "")
    (command "line" p73 p74 p75 p76 p77 p78 "")
    (command "line" p79 p80 p81 p82 p83 "")
    (command "line" p83 p84 p85 p86 p87 p88 p89 p90 p91 p92 p93 "")
    (command "line" p93 p94 p95 "")
    (command "line" p96 p97 p98 p99 p100 p101 p102 p103 "")

    (command "line" p103 p104 p105 p106 p107 p108 p109 p110 p111 p112 "")
    (command "line" p113 p114 p115 p116 p117 p118 p119 p120 p121 p122 p123 "")
    (command "line" p123 p124 p125 p126 p127 p128 p129 p130 p131 p132 "")
    (command "line" p133 p134 p135 p136 p137 p138 p139 p140 p141 p142 p143 "")
    (command "line" p143 p144 p145 p146 p147 p148 p149 p150 p151 p152 p153 "")
    (command "line" p154 p155 p156 p157 p158 p159 p160 p161 p162 p163 "")
    (command "line" p163 p164 p165 p166 p167 p168 p169 p170 p171 p172 p173 "")
    (command "line" p173 p174 p175 "")
    (command "line" p176 p177 p178 p179 p180 p181 p182 p183 "")
    (command "line" p183 p184 p185 p186 p187 p188 p189 p190 p191 p192 p193 "")
    (command "line" p193 p194 p195 p196 p197 p198 "")
    (command "line" p199 p200 p201 p202 p203 "")

    (command "line" p203 p204 p205 p206 p207 p208 p209 p210 p211 p212 p213 "")
    (command "line" p213 p214 p215 p216 p217 p218 p219 p220 p221 p222 "")
    (command "line" p223 p224 p225 p226 p227 p228 p229 p230 p231 p232 p233 "")
    (command "line" p233 p234 p235 p236 p237 p238 p239 p240 p241 p242 p243 "")
    (command "line" p243 p244 p245 p246 p247 p248 "")
    (command "line" p249 p250 p251 p252 p253 "")
    (command "line" p253 p254 p255 p256 p257 p258 p259 p260 p261 p262 p263 "")
    (command "line" p263 p264 p265 p266 p267 p268 p269 p270 p271 p272 p273 "")
    (command "line" p273 p274 p275 p276 "")
    (command "line" p277 p278 p279 p280 p281 p282 p283 "")
    (command "line" p283 p284 p285 p286 p287 p288 p289 p290 p291 p292 p293 "")
    (command "line" p293 p294 p295 p296 p297 p298 p299 p300 p301 p302 p303 "")

    (command "line" p303 p304 p305 p306 "")
    (command "line" p307 p308 p309 p310 p311 p312 p313 "")
    (command "line" p313 p314 p315 p316 p317 p318 p319 p320 p321 p322 p323 "")
    (command "line" p323 p324 p325 p326 p327 p328 p329 p330 p331 p332 p333 "")
    (command "line" p333 p334 p335 p336 p337 "")
    (command "line" p338 p339 p340 p341 p342 p343 "")
    (command "line" p343 p344 p345 p346 p347 p348 p349 p350 p351 p352 p353 "")
    (command "line" p353 p354 p355 p356 p357 p358 p359 p360 p361 p362 p363 "")
    (command "line" p363 p364 p365 p366 p367 p368 p369 "")
    (command "line" p370 p371 p372 p373 "")
    (command "line" p373 p374 p375 p376 p377 p378 p379 p380 p381 p382 p383 "")
    (command "line" p383 p384 p385 p386 p387 p388 p389 p390 p391 p392 p393 "")
    (command "line" p393 p394 p395 p396 p397 p398 p399 p400 p401 p402 "")

    (command "line" p403 p404 p405 p406 p407 p408 p409 p410 p411 p412 p413 "")
    (command "line" p413 p414 p415 p416 p417 p418 p419 p420 p421 p422 p423 "")
    (command "line" p423 p424 p425 p426 p427 p428 p429 p430 p431 p432 p433 "")
    (command "line" p433 p434 p435 "")
    (command "line" p436 p437 p438 p439 p440 p441 p442 p443 "")
    (command "line" p443 p444 p445 p446 p447 p448 p449 p450 p451 p452 p453 "")
    (command "line" p453 p454 p455 p456 p457 p458 p459 p460 p461 p462 p463 "")
    (command "line" p463 p464 p465 p466 p467 p468 "")
    (command "line" p469 p470 p471 p472 p473 "")
    (command "line" p473 p474 p475 p476 p477 p478 p479 p480 p481 p482 p483 "")
    (command "line" p483 p484 p485 p486 p487 p488 p489 p490 p491 p492 p493 "")
    (command "line" p493 p494 p495 p496 p497 p498 p499 p500 p501 "")

    (command "line" p502 p503 p504 p505 p506 p507 p508 p509 p510 p511 p512 p513 "")
    (command "line" p513 p514 p515 p516 p517 p518 p519 p520 p521 p522 p523 "")
    (command "line" p523 p524 p525 p526 p527 p528 p529 p530 p531 p532 p533 "")
    (command "line" p534 p535 p536 p537 p538 p539 p540 p541 p542 p543 "")
    (command "line" p543 p544 p545 p546 p547 p548 p549 p550 p551 p552 p553 "")
    (command "line" p553 p554 p555 p556 p557 p558 p559 p560 p561 p562 p563 "")
    (command "line" p563 p564 p565 "")
    (command "line" p566 p567 p568 p569 p570 p571 p572 p573 "")
    (command "line" p573 p574 p575 p576 p577 p578 p579 p580 p581 p582 p583 "")
    (command "line" p583 p584 p585 p586 p587 p588 p589 p590 p591 p592 p593 "")
    (command "line" p593 p594 p595 p596 "")
    (command "line" p597 p598 p599 p600 p601 p602 p603 "")

    (command "line" p603 p604 p605 p606 p607 p608 p609 p610 p611 p612 p613 "")
    (command "line" p613 p614 p615 p616 p617 p618 p619 p620 p621 p622 p623 "")
    (command "line" p623 p624 p625 p626 "")
    (command "line" p627 p628 p629 p630 p631 p632 p633 "")
    (command "line" p633 p634 p635 p636 p637 p638 p639 p640 p641 p642 p643 "")
    (command "line" p643 p644 p645 p646 p647 p648 p649 p650 p651 p652 p653 p654 "")
    (command "line" p655 p656 p657 p658 p659 p660 p661 p662 p663 "")
    (command "line" p663 p664 p665 p666 p667 p668 p669 p670 p671 p672 p673 "")
    (command "line" p673 p674 p675 p676 p677 p678 p679 "")
    (command "line" p680 p681 p682 p683 "")
    (command "line" p683 p684 p685 p686 p687 p688 p689 p690 p691 p692 p693 "")
    (command "line" p693 p694 p695 p696 p697 p698 p699 p700 "")
    (command "line" p701 p702 p703 "")

    (command "line" p703 p704 p705 p706 p707 p708 p709 p710 p711 p712 p713 "")
    (command "line" p713 p714 p715 p716 "")
)

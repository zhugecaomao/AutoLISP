(defun c:lpbushb()
(setq F (getvar "blipmode")) (setvar "blipmode" 0)
(setq p (getpoint "Insert point:"))
(setq D (getreal "\n Enter diameter [16] [20] [25] [30] [35] [40] [50] [60]:"))
(setq L (getreal "Enter lpbushb length:"))
(setq A (getreal "Enter lpbushb angle:"))
(setq B (* pi (/ A 180)))
(if (= D 16) (setq D1 25.0))
(if (= D 20) (setq D1 30.0))
(if (= D 25) (setq D1 35.0))
(if (= D 30) (setq D1 42.0))
(if (= D 35) (setq D1 48.0))
(if (= D 40) (setq D1 55.0))
(if (= D 50) (setq D1 70.0))
(if (= D 60) (setq D1 80.0))
(setq p1 (polar p B L))
(setq p2 (polar p (- B (/ pi 2)) (+ (/ D 2) 1)))
(setq p6 (polar p (- B (/ pi 2)) (- (/ D1 2) 1)))
(setq p4 (polar p1 (- B (/ pi 2)) (+ (/ D 2) 1)))
(setq p8 (polar p1 (- B (/ pi 2)) (- (/ D1 2) 1)))
(setq p3 (polar p2 (+ B (/ pi 4)) (sqrt 2)))
(setq p7 (polar p6 (- B (/ pi 4)) (sqrt 2)))
(setq p5 (polar p4 (+ B (* pi 0.75)) (sqrt 2)))
(setq p9 (polar p8 (- B (* pi 0.75)) (sqrt 2)))
(command "line" p2 p3 p5 p4 "")
(command "line" p8 p9 p7 p6 "")
(setq p10 (polar p (+ B (/ pi 2)) (+ (/ D 2) 1)))
(setq p14 (polar p (+ B (/ pi 2)) (- (/ D1 2) 1)))
(setq p13 (polar p1 (+ B (/ pi 2)) (+ (/ D 2) 1)))
(setq p17 (polar p1 (+ B (/ pi 2)) (- (/ D1 2) 1)))
(setq p11 (polar p10 (- B (/ pi 4)) (sqrt 2)))
(setq p15 (polar p14 (+ B (/ pi 4)) (sqrt 2)))
(setq p16 (polar p17 (+ B (* pi 0.75)) (sqrt 2)))
(setq p12 (polar p13 (- B (* pi 0.75)) (sqrt 2)))
(command "line" p10 p11 p12 p13 "")
(command "line" p17 p16 p15 p14 "")
(command "line" p12 p5 "")
(setvar "blipmode" F))

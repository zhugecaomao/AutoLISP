DEFUN C:LTR
;(IF (= (TYPE F1) 'FILE ) "YES"  (STOP))
;(IF (= (TYPE F2) 'FILE ) "YES" (STOP))
(setq a1 (entget (car (entsel"\nSelect line:"))))
(setq CIR (entget (car (entsel"\nSelect CIRCLE:"))))
(setq PUT (GETPOINT "\nWHERE DO YOU PUT:"))
(SETQ ET1 (CDR (ASSOC 11 A1)))  ;right
(SETQ ET2 (CDR (ASSOC 10 A1)))  ;right
(SETQ CIRP (CDR (ASSOC 10 CIR)))  ;right
(SETQ R (CDR (ASSOC 40 CIR))) ;right
(setq ETL R)
(SETQ D1 (DISTANCE ET1  ET2))
(SETQ CIRCUM (*  2 3.1416 R))
(SETQ CL (/ D1 CIRCUM))
(SETQ ANGPR (ANGLE CIRP PUT));ANGLE CIRP AND PUT POINT
(SETQ ANGPR (RTD ANGPR))
(SETQ ANGO (* CL 360))
(SETQ ANGL1 (RTOS ANGO 2 2))
(SETQ ANGL1 (ATOI ANGL1))
(IF (<= ANGL1 90)
    (SETQ ANGL1 (+ ANGL1 ANGPR))
)
(SETQ ANGL1 (RTOS ANGL1 2 2))
(SETQ ETL (RTOS ETL 2 2))
(SETQ ENTP1 (STRCAT "@" ETL "<" ANGL1))
(COMMAND "LINE" CIRP PUT "")
(COMMAND "LINE" CIRP ENTP1 "")
(PROMPT "OR YOU CAN DRAW A LINE IT'S ANGLE IS :")
(EVAL ANGO)

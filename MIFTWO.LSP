(VMON)
;--------------------
;Mirror two
(DEFUN C:MIFTWO (/ SS1 EN1 EN2 EN3 NU1)
;(IF (= (TYPE F1) 'FILE ) "YES"  (STOP))
;(IF (= (TYPE F2) 'FILE ) "YES" (STOP))
 (MENUCMD "S=X")
 (SETVAR "ORTHOMODE" 1)
 (SETQ EN1 (ENTLAST))
 (SETQ SS1 (SSGET))
 (COMMAND "MIRROR" SS1 "" PAUSE PAUSE "N")
 (SETQ EN3 (ENTLAST))
 (SETQ NU1 (SSLENGTH SS1))
 (WHILE (NOT (EQUAL EN3 EN1))
   (SETQ EN2 (ENTNEXT EN1))
   (SETQ SS1 (SSADD EN2 SS1))
   (SETQ EN1 EN2)
 )
 (COMMAND "MIRROR" SS1 "" PAUSE PAUSE "N")
 (PRINC)
)

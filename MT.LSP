(VMON)
(setq jona 1 LEO 0 METAL 6461
      chris 1
)
;
(setvar "cmdecho" 0)
(defun dtr (a)
    (* pi (/ a 180.0))
)
;
(defun tan(a)
   (/ (sin a) (cos a))
)
;
;
(defun rel (p x y)
         (setq pp (list (+ (car p) x) (+ (cadr p) y)))
)
;
(defun RELATIVE ()
             (setq p (getpoint "\nRelative PT: "))
             (setq X (getREAL "\nRelative X-distance: "))
             (setq Y (getREAL "\nRelative Y-distance: "))
             (setq p (LIST (+ (CAR P) X) (+ (CADR P) Y)))
)
;
(defun inter1()
   (princ "\nChoose Two Line: ")
   (setq a (ssget))
  (setq b1 (entget (ssname a 0)))
  (setq l11 (cdr (assoc 10 b1)))
  (setq l12 (cdr (assoc 11 b1)))
  (setq b2 (entget (ssname a 1)))
  (setq l21 (cdr (assoc 10 b2)))
  (setq l22 (cdr (assoc 11 b2)))
  (setq p (inters l11 l12 l21 l22 nil))
)
;

(defun del_layer(l)
  (setq S (ssget "X" (list (cons 8 L))))
    (command "ERASE" S "")            ; Delete 'em!
)
;
(defun save_layer()
  (setq la (getvar "clayer"))
)
;
(defun set_layer(lL)
  (command "layer" "s" lL "")
)
(defun brk(dia p)
  (command "break" (polar p (+ (dtr 90) ang) 2) "f" (polar p (+ ang (dtr 90)) (/ dia 2.0))
           (polar p (- ang (dtr 90)) (/ dia 2.0))
  )
)
(defun 16c()
  (SETQ CP (GETVAR "viewctr"))
   (SETQ VSIZE (GETVAR "viewsize"))
   (setq hsize (* 1.3784 vsize))
   (setq ystep (/ vsize 26))
   (setq xstep (/ hsize 15))
    (COMMAND "LAYER" "M" "COLO" "C" "1" "COLO" "")
     (SETQ P1 (POLAR (polar cp (dtr 0) (/ hsize 2.0)) (DTR 90) (/ VSIZE 2.0)))
     (setq p (rel p1 (- 0 xstep) (- 0 (* ystep 2))))
       (SETQ N 1)
  (WHILE (<= N 16)
      (COMMAND "COLOR" N)
         (COLO P)
       (SETQ N (+ N 1))
       (SETQ P (REL P 0 (- 0 ystep)))
  )
      (COMMAND "COLOR" "bylayer")
)
;
(DEFUN COLO(P)
       (COMMAND "SOLID" P (POLAR P (DTR 270) ystep) (POLAR P (DTR 0) xstep)
                         (REL P xstep (- 0 ystep)) ""
       )
)
;
(TERPRI)
(princ "\n..... METAL TECH CO;LTD  TEL:(02)299-1010,299-4090 ....")
(SETQ ORIGINP '(0 0 0))
(setq pline "pline")
(setq center "center")
(setq dash "dash")
(setq dim "dim")
(setq divide "divide")
(setq TEMP "TEMP")
(setq SCREW "SCREW")
(setq WATER "WATER")
(setq DWG "DWG")
(PRINC)

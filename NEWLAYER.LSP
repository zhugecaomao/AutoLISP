defun c:TT
(COMMAND "SETVAR" "CMDECHO" 0)
(COMMAND "LAYER" "MAKE" "9" "COLOR" "9" "9" "LT" "HIDDEN" "9" "")
(COMMAND "LAYER" "MAKE" "DRAW" "COLOR" "2" "DRAW" "LT" "CONTINUOUS" "DRAW" "")
(COMMAND "LAYER" "MAKE" "DRAW-EJ" "COLOR" "2" "DRAW-EJ" "LT" "CONTINUOUS" "DRAW-EJ" "")
(COMMAND "LAYER" "MAKE" "CENTER" "COLOR" "1" "CENTER" "LT" "CENTER" "CENTER" "")
(COMMAND "LAYER" "MAKE" "CENTER-W" "COLOR" "1" "CENTER-W" "LT" "CENTER" "CENTER-W" "")
(COMMAND "LAYER" "MAKE" "HIDDEN" "COLOR" "3" "HIDDEN" "LT" "HIDDEN" "HIDDEN" "")
(COMMAND "LAYER" "MAKE" "HIDDEN-W" "COLOR" "3" "HIDDEN-W" "LT" "HIDDEN" "HIDDEN-W" "")
(COMMAND "LAYER" "MAKE" "TEXT" "COLOR" "4" "TEXT" "LT" "CONTINUOUS" "TEXT" "")
(COMMAND "LAYER" "MAKE" "TEXT-1" "COLOR" "4" "TEXT-1" "LT" "CONTINUOUS" "TEXT-1" "")
(COMMAND "LAYER" "MAKE" "DIM3" "COLOR" "4" "DIM3" "LT" "CONTINUOUS" "DIM3" "")
(COMMAND "LAYER" "MAKE" "PHANTOM" "COLOR" "5" "PHANTOM" "LT" "PHANTOM" "PHANTOM" "")
(COMMAND "LAYER" "MAKE" "MAGENTA" "COLOR" "6" "MAGENTA" "LT" "PHANTOM" "MAGENTA" "")
(COMMAND "LAYER" "MAKE" "DIM" "COLOR" "5" "DEFPOINTS" "LT" "CONTINUOUS" "CONTINUOUS" "")
(COMMAND "LAYER" "MAKE" "SCREW" "COLOR" "7" "0" "LT" "CONTINUOUS" "SCREW" "")
(COMMAND "LAYER" "MAKE" "0" "COLOR" "7" "0" "LT" "CONTINUOUS" "0" "")

(defun c:NOT(/ ocm obl olderr pt ang opl)
  (setq ocm (getvar "cmdecho") 
        obl (getvar "blipmode")
        olderr *ERROR*
         *error* ai_abort)
  (setvar "cmdecho" 0) (setvar "blipmode"0)
  (initget 1)
  (setq pt (getpoint "\n插入点: "))
  (initget 0)
  (setq ang (getint "\n旋转角度<0>: "))
  (if (= ang nil) (setq ang 0))
  (setq lx_xy (open "c:/Autolisp/data.dat" "r")) 
  (setq l_xxy (read-line lx_xy))
  (setq l_xy (read l_xxy))
  (close lx_xy)
  (setq opl (car l_xy))
  (command "insert" "c:/Autolisp/block/HAND.dwg" pt (* opl 0.00015) "" ang)
  (setvar "cmdecho" ocm) (setvar "blipmode" obl)
  (setq *error* olderr)
  (princ)
)

(defun c:pip (/ X f p0 angle p1 p2 p3 )
(setq x (getint "Enter the radius = "))
(setq p0 (getpoint "Enter insert point "))
(setq angle (getangle "Angle = "))
(setq y (getdist "Enter weld point distance = "))
(setq p1 (polar p0 (+ angle (/ (* pi 5 ) 6)) (/ X 50)))
(setq p2 (polar p0 (- angle (/ (* pi 5 ) 6)) (/ X 50)))
(setq p4 (polar p0 (+ angle pi) (/ y 50)))
(setq p5 (polar p0 angle (/ y 50)))
(setq p3 (polar p0 angle (/ X 50)))
(command "arc" p2 p3 p1 )
(command "break" p0 p3 )
(command "donut" "0" "2" p4 p5 "")
(princ)
)

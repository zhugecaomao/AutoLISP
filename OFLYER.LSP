(DEFUN C:OFLYER()
(SETQ LY (GETVAR "CLAYER"))
(PROMPT"\n<Offset distance>:")
(IF (= OFT NIL)
      (SETQ OFT 0.0)
)
(PROMPT "\nOffset distance :<") (PRIN1 OFT)(PROMPT">")
(SETQ OFTL (GETDIST"\nOffset Distance or Throught<Throught>:"))
(IF (= OFTL NIL)
    (SETQ OFTL OFT)
)
(SETQ OFT OFTL)
(REPEAT 10
  (SETQ SF2 (ENTSEL "\nSelect object to offset:"))
  (SETQ SF3 (GETPOINT "\nSide to offset?"))
  (SETQ HP (CADR SF2))
  (COMMAND "SELECT" HP "")
  (COMMAND "OFFSET" OFTL HP SF3 "")
  (SETQ LR LY)
  (SETQ S1 "L")
  (IF S1 (COMMAND "CHANGE" S1 "" "P" "COLOR" "BYLAYER" "LT" "BYLAYER" "LA" LR ""))
)
)

(DEFUN C:PIN ()
   (SETVAR "CMDECHO" 0)
   (SETQ VC (GETVAR "VIEWCTR"))
   (SETQ YR (GETVAR "VIEWSIZE"))
   (SETQ XR (* YR 1.3864))
   (SETQ YD (/ YR 10))
   (SETQ XD (/ XR 9))
   (SETQ XB (- (CAR VC) (/ XR 2)))
   (SETQ YB (- (CADR VC) (/ YR 2)))
   (COMMAND "VSLIDE" "C:/ACAD/SLIDE/PIN")
;----
   (SETQ PT (GETPOINT "\nPLEASE DIGIT THE CHAR. TABLE : "))
             (SETQ XP (CAR PT))
             (SETQ YP (CADR PT))
             (SETQ XAA (- XP XB))
             (SETQ YAA (- YP YB))
             (SETQ XA (ABS XAA))
             (SETQ YA (ABS YAA))
             (SETQ X (FIX ( / XA XD)))
             (SETQ Y (FIX ( / YA YD)))
;
      (IF (AND (= X 1) (= Y 0))
      (COMMAND "REDRAW" "INSERT" "C:/ACAD/BLOCK/EJ5-0" PAUSE 1 1 0))
      (IF (AND (= X 2) (= Y 0))
      (COMMAND "REDRAW" "INSERT" "C:/ACAD/BLOCK/EJ5-5" PAUSE 1 1 0))
      (IF (AND (= X 3) (= Y 0))
      (COMMAND "REDRAW" "INSERT" "C:/ACAD/BLOCK/EJ6-0" PAUSE 1 1 0))
      (IF (AND (= X 4) (= Y 0))
      (COMMAND "REDRAW" "INSERT" "C:/ACAD/BLOCK/EJ8-0" PAUSE 1 1 0))
      (IF (AND (= X 5) (= Y 0))
      (COMMAND "REDRAW" "INSERT" "C:/ACAD/BLOCK/EJ10-0" PAUSE 1 1 0))
      (IF (AND (= X 6) (= Y 0))
      (COMMAND "REDRAW" "INSERT" "C:/ACAD/BLOCK/EJ12-0" PAUSE 1 1 0))
      (IF (AND (= X 7) (= Y 0))
      (COMMAND "REDRAW" "INSERT" "C:/ACAD/BLOCK/EJ14-0" PAUSE 1 1 0))
      (IF (AND (= X 8) (= Y 0))
      (COMMAND "REDRAW" "INSERT" "C:/ACAD/BLOCK/EJ15-0" PAUSE 1 1 0))
      (IF (AND (= X 1) (= Y 1))
      (COMMAND "REDRAW" "INSERT" "C:/ACAD/BLOCK/EJ1-0" PAUSE 1 1 0))
      (IF (AND (= X 2) (= Y 1))
      (COMMAND "REDRAW" "INSERT" "C:/ACAD/BLOCK/EJ1-5" PAUSE 1 1 0))
      (IF (AND (= X 3) (= Y 1))
      (COMMAND "REDRAW" "INSERT" "C:/ACAD/BLOCK/EJ2-0" PAUSE 1 1 0))
      (IF (AND (= X 4) (= Y 1))
      (COMMAND "REDRAW" "INSERT" "C:/ACAD/BLOCK/EJ2-5" PAUSE 1 1 0))
      (IF (AND (= X 5) (= Y 1))
      (COMMAND "REDRAW" "INSERT" "C:/ACAD/BLOCK/EJ3-0" PAUSE 1 1 0))
      (IF (AND (= X 6) (= Y 1))
      (COMMAND "REDRAW" "INSERT" "C:/ACAD/BLOCK/EJ3-5" PAUSE 1 1 0))
      (IF (AND (= X 7) (= Y 1))
      (COMMAND "REDRAW" "INSERT" "C:/ACAD/BLOCK/EJ4-0" PAUSE 1 1 0))
      (IF (AND (= X 8) (= Y 1))
      (COMMAND "REDRAW" "INSERT" "C:/ACAD/BLOCK/EJ4-5" PAUSE 1 1 0))
      (IF (AND (= X 0) (= Y 2))
      (COMMAND "REDRAW" "INSERT" "C:/ACAD/BLOCK/SP60" PAUSE 1 1 0))
      (IF (AND (= X 1) (= Y 2))
      (COMMAND "REDRAW" "INSERT" "C:/ACAD/BLOCK/SP65" PAUSE 1 1 0))
      (IF (AND (= X 2) (= Y 2))
      (COMMAND "REDRAW" "INSERT" "C:/ACAD/BLOCK/SP70" PAUSE 1 1 0))
      (IF (AND (= X 3) (= Y 2))
      (COMMAND "REDRAW" "INSERT" "C:/ACAD/BLOCK/SP75" PAUSE 1 1 0))
      (IF (AND (= X 4) (= Y 2))
      (COMMAND "REDRAW" "INSERT" "C:/ACAD/BLOCK/SP80" PAUSE 1 1 0))
      (IF (AND (= X 5) (= Y 2))
      (COMMAND "REDRAW" "INSERT" "C:/ACAD/BLOCK/SP85" PAUSE 1 1 0))
      (IF (AND (= X 6) (= Y 2))
      (COMMAND "REDRAW" "INSERT" "C:/ACAD/BLOCK/SP90" PAUSE 1 1 0))
      (IF (AND (= X 7) (= Y 2))
      (COMMAND "REDRAW" "INSERT" "C:/ACAD/BLOCK/SP95" PAUSE 1 1 0))
      (IF (AND (= X 8) (= Y 2))
      (COMMAND "REDRAW" "INSERT" "C:/ACAD/BLOCK/SP100" PAUSE 1 1 0))
      (IF (AND (= X 1) (= Y 3))
      (COMMAND "REDRAW" "INSERT" "C:/ACAD/BLOCK/SP20" PAUSE 1 1 0))
      (IF (AND (= X 2) (= Y 3))
      (COMMAND "REDRAW" "INSERT" "C:/ACAD/BLOCK/SP25" PAUSE 1 1 0))
      (IF (AND (= X 3) (= Y 3))
      (COMMAND "REDRAW" "INSERT" "C:/ACAD/BLOCK/SP30" PAUSE 1 1 0))
      (IF (AND (= X 4) (= Y 3))
      (COMMAND "REDRAW" "INSERT" "C:/ACAD/BLOCK/SP35" PAUSE 1 1 0))
      (IF (AND (= X 5) (= Y 3))
      (COMMAND "REDRAW" "INSERT" "C:/ACAD/BLOCK/SP40" PAUSE 1 1 0))
      (IF (AND (= X 6) (= Y 3))
      (COMMAND "REDRAW" "INSERT" "C:/ACAD/BLOCK/SP45" PAUSE 1 1 0))
      (IF (AND (= X 7) (= Y 3))
      (COMMAND "REDRAW" "INSERT" "C:/ACAD/BLOCK/SP50" PAUSE 1 1 0))
      (IF (AND (= X 8) (= Y 3))
      (COMMAND "REDRAW" "INSERT" "C:/ACAD/BLOCK/SP55" PAUSE 1 1 0))
      (IF (AND (= X 1) (= Y 4))
      (COMMAND "REDRAW" "INSERT" "C:/ACAD/BLOCK/EGP16" PAUSE 1 1 0))
      (IF (AND (= X 2) (= Y 4))
      (COMMAND "REDRAW" "INSERT" "C:/ACAD/BLOCK/EGP20" PAUSE 1 1 0))
      (IF (AND (= X 3) (= Y 4))
      (COMMAND "REDRAW" "INSERT" "C:/ACAD/BLOCK/EGP25" PAUSE 1 1 0))
      (IF (AND (= X 4) (= Y 4))
      (COMMAND "REDRAW" "INSERT" "C:/ACAD/BLOCK/EGP30" PAUSE 1 1 0))
      (IF (AND (= X 5) (= Y 4))
      (COMMAND "REDRAW" "INSERT" "C:/ACAD/BLOCK/EGP35" PAUSE 1 1 0))
      (IF (AND (= X 6) (= Y 4))
      (COMMAND "REDRAW" "INSERT" "C:/ACAD/BLOCK/EGP40" PAUSE 1 1 0))
      (IF (AND (= X 1) (= Y 5))
      (COMMAND "REDRAW" "INSERT" "C:/ACAD/BLOCK/RP12" PAUSE 1 1 0))
      (IF (AND (= X 2) (= Y 5))
      (COMMAND "REDRAW" "INSERT" "C:/ACAD/BLOCK/RP15" PAUSE 1 1 0))
      (IF (AND (= X 3) (= Y 5))
      (COMMAND "REDRAW" "INSERT" "C:/ACAD/BLOCK/RP20" PAUSE 1 1 0))
      (IF (AND (= X 4) (= Y 5))
      (COMMAND "REDRAW" "INSERT" "C:/ACAD/BLOCK/RP25" PAUSE 1 1 0))
      (IF (AND (= X 5) (= Y 5))
      (COMMAND "REDRAW" "INSERT" "C:/ACAD/BLOCK/RP30" PAUSE 1 1 0))
      (IF (AND (= X 1) (= Y 6))
      (COMMAND "REDRAW" "INSERT" "C:/ACAD/BLOCK/GB16-1" PAUSE 1 1 0))
      (IF (AND (= X 2) (= Y 6))
      (COMMAND "REDRAW" "INSERT" "C:/ACAD/BLOCK/GB20-1" PAUSE 1 1 0))
      (IF (AND (= X 3) (= Y 6))
      (COMMAND "REDRAW" "INSERT" "C:/ACAD/BLOCK/GB25-1" PAUSE 1 1 0))
      (IF (AND (= X 4) (= Y 6))
      (COMMAND "REDRAW" "INSERT" "C:/ACAD/BLOCK/GB30-1" PAUSE 1 1 0))
      (IF (AND (= X 5) (= Y 6))
      (COMMAND "REDRAW" "INSERT" "C:/ACAD/BLOCK/GB35-1" PAUSE 1 1 0))
      (IF (AND (= X 6) (= Y 6))
      (COMMAND "REDRAW" "INSERT" "C:/ACAD/BLOCK/GB40-1" PAUSE 1 1 0))
      (IF (AND (= X 7) (= Y 6))
      (COMMAND "REDRAW" "INSERT" "C:/ACAD/BLOCK/GB50-1" PAUSE 1 1 0))
      (IF (AND (= X 1) (= Y 7))
      (COMMAND "REDRAW" "INSERT" "C:/ACAD/BLOCK/GB16" PAUSE 1 1 0))
      (IF (AND (= X 2) (= Y 7))
      (COMMAND "REDRAW" "INSERT" "C:/ACAD/BLOCK/GB20" PAUSE 1 1 0))
      (IF (AND (= X 3) (= Y 7))
      (COMMAND "REDRAW" "INSERT" "C:/ACAD/BLOCK/GB25" PAUSE 1 1 0))
      (IF (AND (= X 4) (= Y 7))
      (COMMAND "REDRAW" "INSERT" "C:/ACAD/BLOCK/GB30" PAUSE 1 1 0))
      (IF (AND (= X 5) (= Y 7))
      (COMMAND "REDRAW" "INSERT" "C:/ACAD/BLOCK/GB35" PAUSE 1 1 0))
      (IF (AND (= X 6) (= Y 7))
      (COMMAND "REDRAW" "INSERT" "C:/ACAD/BLOCK/GB40" PAUSE 1 1 0))
      (IF (AND (= X 7) (= Y 7))
      (COMMAND "REDRAW" "INSERT" "C:/ACAD/BLOCK/GB50" PAUSE 1 1 0))
      (IF (AND (= X 1) (= Y 8))
      (COMMAND "REDRAW" "INSERT" "C:/ACAD/BLOCK/GP16-1" PAUSE 1 1 0))
      (IF (AND (= X 2) (= Y 8))
      (COMMAND "REDRAW" "INSERT" "C:/ACAD/BLOCK/GP20-1" PAUSE 1 1 0))
      (IF (AND (= X 3) (= Y 8))
      (COMMAND "REDRAW" "INSERT" "C:/ACAD/BLOCK/GP25-1" PAUSE 1 1 0))
      (IF (AND (= X 4) (= Y 8))
      (COMMAND "REDRAW" "INSERT" "C:/ACAD/BLOCK/GP30-1" PAUSE 1 1 0))
      (IF (AND (= X 5) (= Y 8))
      (COMMAND "REDRAW" "INSERT" "C:/ACAD/BLOCK/GP35-1" PAUSE 1 1 0))
      (IF (AND (= X 6) (= Y 8))
      (COMMAND "REDRAW" "INSERT" "C:/ACAD/BLOCK/GP40-1" PAUSE 1 1 0))
      (IF (AND (= X 7) (= Y 8))
      (COMMAND "REDRAW" "INSERT" "C:/ACAD/BLOCK/GP50-1" PAUSE 1 1 0))
      (IF (AND (= X 1) (= Y 9))
      (COMMAND "REDRAW" "INSERT" "C:/ACAD/BLOCK/GP16" PAUSE 1 1 0))
      (IF (AND (= X 2) (= Y 9))
      (COMMAND "REDRAW" "INSERT" "C:/ACAD/BLOCK/GP20" PAUSE 1 1 0))
      (IF (AND (= X 3) (= Y 9))
      (COMMAND "REDRAW" "INSERT" "C:/ACAD/BLOCK/GP25" PAUSE 1 1 0))
      (IF (AND (= X 4) (= Y 9))
      (COMMAND "REDRAW" "INSERT" "C:/ACAD/BLOCK/GP30" PAUSE 1 1 0))
      (IF (AND (= X 5) (= Y 9))
      (COMMAND "REDRAW" "INSERT" "C:/ACAD/BLOCK/GP35" PAUSE 1 1 0))
      (IF (AND (= X 6) (= Y 9))
      (COMMAND "REDRAW" "INSERT" "C:/ACAD/BLOCK/GP40" PAUSE 1 1 0))
      (IF (AND (= X 7) (= Y 9))
      (COMMAND "REDRAW" "INSERT" "C:/ACAD/BLOCK/GP50" PAUSE 1 1 0))
      )

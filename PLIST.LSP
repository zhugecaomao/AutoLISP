(defun c:plist()
  (setq G (getvar "blipmode")) (setvar "blipmode" 0)
  (setq D())
  (setq A1 (getstring "\n Enter DATA'S file: "))
  (setq A (strcat A1 ".txt"))
  (setq B (open A "r"))
  (setq C (read-line B))
  (while C
    (setq C1 (substr C 1 63))
    (setq D (cons C1 D))
    (setq C (read-line B))
  )
  (close B)
  (setq F (length D))
  (setq E (getreal "\n Scaling factor: 1=190mm <1> "))
  (if (eq E nil) (setq E 1.0))
  (setq P(osnap (getpoint
    "\n Toush upper right conner of drawing; ") "end"))
  (setq P1(list (- (car P) (* 95 E)) (- (cadr P) (* 5 E))))
  (setq P2 (list (- (car P) (* 185 E)) (- (cadr P) (* 10 E))))
  (setq P3 (list (- (car P) (* 150 E)) (cadr p2)))
  (setq P4 (list (- (car P) (* 115 E)) (cadr p2)))
  (setq P5 (list (- (car P) (* 70 E)) (cadr p2)))
  (setq P6 (list (- (car P) (* 25 E)) (cadr p2)))
  (setq P7 (list (- (car P) (* 5 E)) (- (cadr p2) 0.25)))
  (setq P71 (list (car P7) (+ (cadr P7) 2)))
  (command "text" "c" P1 (* 4 E) 0 "PART LIST")
  (command "text" "c" P2 (* 3 E) 0 "PT")
  (command "text" "c" p3 (* 3 E) 0 "DESCRIPTION")
  (command "text" "c" P4 (* 3 E) 0 "No")
  (command "text" "c" P5 (* 3 E) 0 "STOCK SIZE")
  (command "text" "c" P6 (* 3 E) 0 "MAT'L")
  (command "text" "c" P71 (* 1.5 E) 0 "DRAG")
  (command "text" "c" P7 (* 1.5 E) 0 "No")
  (setq B (open A "r"))
  (setq P8(list (car P2) (- (cadr P2) (* 5 E))))
  (repeat F
    (setq P9(list (+ (car P2) (* 7 E)) (cadr P8)))
    (setq P10(list (+ (car P2) (* 70 E)) (cadr P8)))
    (setq P11(list (+ (car P2) (* 77 E)) (cadr P8)))
    (setq P12(list (+ (car P2) (* 147 E)) (cadr P8)))
    (setq P13(list (+ (car P2) (* 180 E)) (cadr P8)))
    (setq C (read-line B))
    (command "text" "C" P8 (* 3 E) 0 (substr C 1 2))
    (command "text" P9 (* 3 E) 0 (substr C 3 20))
    (command "text" "C" P10 (* 3 E) 0 (substr C 23 2))
    (command "text" P11 (* 3 E) 0 (substr C 25 28))
    (command "text" P12 (* 3 E) 0 (substr C 53 8))
    (command "text" "c" P13 (* 3 E) 0 (substr C 61 2))
    (setq P8 (list (car P8) (- (cadr P8) (* 5 E))))
    (terpri)
  )
  (setq P14 (list (- (car P) (* 190 E)) (cadr P)))
  (setq P15 (list (- (car P) (* 180 E)) (- (cadr P) (* 6 E))))
  (setq P16 (list (- (car P) (* 120 E)) (cadr P15)))
  (setq P17 (list (- (car P) (* 110 E)) (cadr P15)))
  (setq P18 (list (- (car P) (* 40 E)) (cadr P15)))
  (setq P19 (list (- (car P) (* 10 E)) (cadr P15)))
  (setq P20 (list (car P14) (- (cadr P) (* (+ (* 5 F) 11) E))))
  (setq P21 (list (car P15) (cadr P20)))
  (setq P22 (list (car P16) (cadr P20)))
  (setq P23 (list (car P17) (cadr P20)))
  (setq P24 (list (car P18) (cadr P20)))
  (setq P25 (list (car P19) (cadr P20)))
  (command "line" P14 P20 "")
  (command "line" P15 P21 "")
  (command "line" P16 P22 "")
  (command "line" P17 P23 "")
  (command "line" P18 P24 "")
  (command "line" P19 P25 "")
  (setq P26 (list (car P14) (cadr P15)))
  (setq P27 (list (car P) (cadr P15)))
  (command "line" P26 P27 "")
  (command "array" "l" "" "r" (+ F 2) 1 (* -5 E))
  (setvar "blipmode" G)
)

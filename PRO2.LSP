(defun C:BUSH-A()
    (setq p (getpoint "\nPlease insert the point :"))
    (setq D (getreal "\nPlease select the diameter size
    '16' '20' '25' '30' '35' '40' '50' '60':"))
    (setq L (getreal "\nPlease enter bush 'A' length:"))
    (setq A (getreal "\nPlease enter the bush 'A' locating angle:"))
    (setq B (* pi (/ A 180)))
    (cond ((= D 16)
	   (setq d1 25 d2 30 h 6))
	  ((= D 20)
	   (setq d1 30 d2 35 h 8))
	  ((= D 25)
	   (setq d1 35 d2 40 h 8))
	  ((= D 30)
	   (setq d1 42 d2 47 h 10))
	  ((= D 35)
	   (setq d1 48 d2 54 h 10))
	  ((= D 40)
	   (setq d1 55 d2 61 h 10))
	  ((= D 50)
	   (setq d1 70 d2 76 h 12))
	  (t (setq d1 80 d2 86 h 12))
    )
(if (> L D) (setq L1 D) (setq L1 L))
(setq p1 (polar p B L))
(setq p2 (polar p1 (+ B pi) H))
(setq p3 (polar p B L1))
(setq p4 (polar p (- B (/ pi 2)) (+ (/ D 2) 1)))
(setq p13 (polar p (- B (/ pi 2)) (- (/ D1 2) 1)))
(setq p14 (polar p (+ B (/ pi 2)) (+ (/ D 2) 1)))
(setq p23 (polar p (+ B (/ pi 2)) (- (/ D1 2) 1)))
(setq p22 (polar p23 (+ B (/ pi 4)) (sqrt 2)))
(setq p5 (polar p4 (+ B (/ pi 4)) (sqrt 2)))
(setq p12 (polar p13 (- B (/ pi 4)) (sqrt 2)))
(setq p15 (polar p14 (- B (/ pi 4)) (sqrt 2)))
(setq p6 (polar p3 (- B (/ pi 2)) (/ D 2)))
(setq p16 (polar p3 (+ B (/ pi 2)) (/ D 2)))
(setq p17 (polar p16 (+ B (/ pi 2)) 0.5))
(setq p7 (polar p6 (- B (/ pi 2)) 0.5))
(setq p11 (polar p2 (- B (/ pi 2)) (/ D1 2)))
(setq p21 (polar p2 (+ B (/ pi 2)) (/ D1 2)))
(setq p20 (polar p2 (+ B (/ pi 2)) (/ D2 2)))
(setq p10 (polar p2 (- B (/ pi 2)) (/ D2 2)))
(setq p9 (polar p1 (- B (/ pi 2)) (/ D2 2)))
(setq p19 (polar p1 (+ B (/ pi 2)) (/ D2 2)))
(setq p18 (polar p17 B (- L L1)))
(setq p8 (polar p7 B (- L L1)))
(command "line" p9 p10 p11 p12 p13 "")
(command "line" p23 p22 p21 p20 p19 "")
(if (> L D)
    (progn
	(command "line" p18 p17 p16 p15 p14 "")
	(command "line" p4 p5 p6 p7 p8 "")
    )
    (progn
	(command "line" p16 p15 p14 "")
	(command "line" p4 p5 p6 "")))
(princ)
)

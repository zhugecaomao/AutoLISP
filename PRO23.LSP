(defun C:int (/ temp1 temp2 p1 p2 ans ln11 ln12 ln21 ln22 inp pd ps)
      (setvar "cmdecho" 0)
      (setq temp1 (entsel "\nSelect the first line :"))
      (redraw  (car temp1) 3)
      (setq temp2 (entsel "\nSelect the second line :"))
      (redraw  (car temp2) 3)
      (redraw  (car temp1) 1)
      (redraw  (car temp2) 1)
      (setq ans (getstring "\nExtending the two line ? (Y/N) <N> :"))
      (if (or (= ans "y")(= ans "Y")(= ans nil))
       (progn
	(setq p1 (nth 1 temp1))
	(setq p2 (nth 1 temp2))
	(command "fillet" "r" "0" )
	(command "fillet" p1 p2 )
       )
       (progn
	(setq pd (getvar "pdmode"))
	(setq ps (getvar "pdsize"))
	(setvar "pdmode" 2)
	(setvar "pdsize" -1)
	(setq temp1 (entget (car temp1)))
	(setq temp2 (entget (car temp2)))
	(setq ln11 (cdr (assoc 10 temp1)))
	(setq ln12 (cdr (assoc 11 temp1)))
	(setq ln21 (cdr (assoc 10 temp2)))
	(setq ln22 (cdr (assoc 11 temp2)))
	(setq inp (inters ln11 ln12 ln21 ln22 nil))
	(command "point" inp)
	(setvar "pdmode" pd)
	(setvar "pdsize" ps)
       )
    )
      (setvar "cmdecho" 1)
)

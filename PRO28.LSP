(defun C:lp-b()
(setq p (getpoint "Please insert point:"))
(setq D (getint "\n Please selet diameter size '16' '20' '25' '30' '35'
'40' '50' '60':"))
(setq L (getint "Please input the cav. plate thickness:"))
(setq L1 (getint "Please input the core plate thickness:"))
(setq A (getreal "Please input the leading pin angle:"))
(setq B (* pi (/ A 180)))
(setq p34 (polar p (+ B (/ pi 2)) (- (* 0.5 D) 1.5)))
(setq p35 (polar p (- B (/ pi 2)) (- (* 0.5 D) 1.5)))
(command "break" p34 p35 "")
(cond ((= d 16)
      (setq d1 30 d2 25 h 6 m 8))
      ((= d 20)
      (setq d1 35 d2 30 h 8 m 10))
      ((= d 25)
      (setq d1 40 d2 35 h 8 m 12))
      ((= d 30)
      (setq d1 47 d2 42 h 10 m 15))
      ((= d 35)
      (setq d1 54 d2 48 h 10 m 15))
      ((= d 40)
      (setq d1 61 d2 55 h 12 m 20))
      ((= d 50)
      (setq d1 76 d2 70 h 15 m 25))
      (t
      (setq d1 86 d2 80 h 15 m 25))
)
(setq p1 (polar p (+ B pi) (- L1 h)))
(setq p2 (polar p1 B 4))
(setq p3 (polar p2 (+ B (/ pi 2)) (- (/ d2 2.0) 0.5)))
(setq p4 (polar p2 (- B (/ pi 2)) (- (/ d2 2.0) 0.5)))
(setq p5 (polar p2 (+ B (/ pi 2)) (/ d2 2.0)))
(setq p6 (polar p2 (- B (/ pi 2)) (/ d2 2.0)))
(setq p9 (polar p1 (+ B (/ pi 2)) (/ d1 2)))
(setq p10 (polar p1 (- B (/ pi 2)) (/ d1 2)))
(setq p11 (polar p9 (+ B pi) h))
(setq p12 (polar p10 (+ B pi) h))
(setq p7 (polar p (+ b (/ pi 2)) (/ d2 2.0)))
(setq p8 (polar p (- B (/ pi 2)) (/ d2 2.0)))
(setq p13 (polar p1 (+ B (/ pi 2)) (- (/ d2 2.0) 0.5)))
(setq p14 (polar p1 (- B (/ pi 2)) (- (/ d2 2.0) 0.5)))
(setq p29 (polar p (+ B pi) 1.5))
(setq p30 (polar p29 (+ B (/ pi 2)) (/ d2 2.0)))
(setq p31 (polar p29 (- B (/ pi 2)) (/ d2 2.0)))
(setq p32 (polar p29 (+ B (/ pi 2)) (/ d 2.0)))
(setq p33 (polar p29 (- B (/ pi 2)) (/ d 2.0)))
(setq p34 (polar p32 B 3.0))
(setq p35 (polar p33 B 3.0))
(command "line" p11 p12 p10 p9 "c")
(command "line" p7 p5 p6 p8 "")
(command "line" p3 p13 "")
(command "line" p4 p14 "")
(command "line" p30 p31 "")
(command "arc" p32 "e" p34 "a" 180)
(command "line" p34 p35 "")
(command "arc" p35 "e" p33 "a" 180)
(setq p15 (polar p B (- L 2)))
(setq p16 (polar p B (- l (+ 2 M))))
(setq p28 (polar p16 B 1.5))
(setq p24 (polar p16 (- B (/ pi 2)) (/ d 2.0)))
(setq p25 (polar p16 (+ B (/ pi 2)) (/ d 2.0)))
(setq p27 (polar p24 (+ B 0.087266) (/ m (cos 0.087266))))
(setq p26 (polar p25 (- B 0.087266) (/ m (cos 0.087266))))
    (if (>= (- L (+ 3 m)) d)
        (progn
            (setq n (/ (- L (+ 3 m)) d))
            (setq x 1)
            (repeat n
                (setq p17 (polar p28 (+ B pi) (* x d)))
                (setq p18 (polar p17 (+ B (/ pi 2)) (/ d 2.0)))
                (setq p19 (polar p17 (- B (/ pi 2)) (/ d 2.0)))
                (setq p20 (polar p19 B 1.5))
                (setq p21 (polar p18 B 1.5))
                (setq p22 (polar p19 B -1.5))
                (setq p23 (polar p18 B -1.5))
                (command "line" p21 (polar p21 B (- d 3.0))
                  (polar p20 B (- d 3.0)) p20 "")
                (command "arc" p23 "e" p21 "a" 180)
                (command "line" p21 p20 "")
                (command "arc" p20 "e" p22 "a" 180)
                (setq x (+ 1 x))
            )
        (command "line" p34 p23 p22 p35 "")
        )
        (command "line" p34 p25 p24 p35 "")
    )
(command "pline" p24 "w" 0 0 p27 p26 p25 "")
(command "fillet" "r" 3.5 "fillet" "p" "l")
)

(defun C:OF2 ()
(setvar "cmdecho" 0)
(setq aa (/ (getreal "\nInput the diameter of W Line: ") 2))
    (command "osnap" "nea")
    (setq x (getpoint "\nSelect the center line of Centet Line : "))
	    (setq bb (ssget x))
	    (command "osnap" "none")
	    (setq sidea (list (+ (car x) 10)(+ (cadr x) 10)))
	    (setq sideb (list (- (car x) 10)(- (cadr x) 10)))
	    (command "osnap" "none")
	    (command "offset" aa x sidea "")
	    (command "change" "last" "" "la" "0")
	    (command "offset" aa x sideb "")
	    (command "change" "last" "" "la" "0")
(command "setvar" "highlight" 1)
(setvar "cmdecho" 1)
(print)
)

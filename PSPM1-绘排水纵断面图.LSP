(defun C:tk2 ()
 (prompt "\n\t\t\现在请输入图框特征")
 (prompt "\n\t***********************************************************")
 (setvar "CMDECHO" 0)
 (setvar "BLIPMODE" 0)
 (setq n (length a))
 (setq i 0 hhb nil llb nil)
 (while (< i n)
  (setq llb (cons (car (cadr (nth i a))) llb))
  (setq hhb (cons (cadr (cadr (nth i a))) hhb))
  (setq i (+ i 1))
 )
 (setq maxl (apply '+ llb))
 (setq maxh (apply 'max hhb))
 (setq minh (apply 'min hhb))
 (setq maxh (+ (cadr pd0) (- maxh minh) 40))
 (setq maxl (+ (car pd0) (* k (+ maxl 20))))
 (prompt (strcat "\n_____你的图形高为" (rtos maxh 2 0) "_____"))
 (setq kd (getdist "\n 输入图框宽;/297/420/594/841/: "))
 (cond ((= kd 297) (setq kc "/420/631/841/1051/1261/")))
 (cond ((= kd 420) (setq kc "/594/743/841/892/1041/1189/")))
 (cond ((= kd 594) (setq kc "/841/1051/1261/")))
 (cond ((= kd 841) (setq kc "/1051/1261/")))
 (prompt (strcat "\n_____你的图形长为" (rtos maxl 2 0) "_____"))
 (setq cd (getdist (strcat "\n 输入图框长;" kc ": ")))
 (command "limits" '(0.0 0.0) (list cd kd))
 (command "zoom" "a")
 (command "grid" 10.0 )
 (command "layer" "new" "tk" "" )
 (command "line" '(0.0 0.0) (list cd 0.0) (list cd kd) (list 0.0
                  kd) "c" )
 (command "pline" '(25.0 10.0) "w" "0.9" "" (list (- cd 10.0) 10.0)
                    (list (- cd 10.0) (- kd 10.0)) (list 25.0 (- kd
                    10.0)) "c" )
 (command "insert" "c:/jiangdh/tl/tq" (list (- cd 10.0) 10.0) "0.01"
          "0.01" "")
 (command "insert" "c:/jiangdh/tl/hq" (list 25.0 (- kd 10.0)) ""
          "" "")
)

(defun nk2 ()
 (command "color" "3")
 (setq dc (+ (car pd0) ll 10.0))
 (command "pline" '(75.0 65.0) "w" "0.3" "" (list dc 65.0)
                  (list dc 195.0) '(75.0 195.0) "c")
 (command "pline" '(75.0 75.0  ) (list dc 75.0) "")
 (command "pline" '(75.0  85.0 ) (list dc 85.0) "")
 (command "pline" '(75.0  100.0) (list dc 100.0) "")
 (command "pline" '(75.0 115.0 ) (list dc 115.0) "")
 (command "pline" '(75.0 122.5 ) (list dc 122.5) "")
 (command "pline" '(75.0 130.0 ) (list dc 130.0) "")
 (command "pline" '(75.0 145.0 ) (list dc 145.0) "")
 (command "pline" '(75.0 160.0 ) (list dc 160.0) "")
 (command "pline" '(75.0 175.0 ) (list dc 175.0) "")
 (command "pline" '(125.0 65.0) '(125.0 195.0) "")
 (command "text" "c" '(100.0 67.5) "5" "0" "检查井尺寸(毫米)")
 (command "text" "c" '(100.0 77.5) "5" "" "检查井编号")
 (command "text" "c" '(100.0 90.0) "5" "" "接入管尺寸(毫米)")
 (command "text" "c" '(100.0 105.0) "5" "" "平 面 距 离(米)")
 (command "text" "c" '(100.0 116.25) "5" "" "坡 度   ")
 (command "insert" "c:/jiangdh/tl/qfh" '(104.0 115.0) "" "" "")
 (command "text" "c" '(100.0 123.75) "5" "" "管径(毫米) 管材")
 (command "text" "c" '(100.0 135.0) "5" "" "埋  深 (米)") 
 (command "text" "c" '(100.0 150.0) "5" "" "设计管内底标高(米)")
 (command "text" "c" '(100.0 165.0) "5" "" "设计地面标高(米)")
 (command "text" "c" '(100.0 182.5) "5" "" "道路里程(桩号)(米)")
)

;***************************** DMX ********************************
(defun dm3 ( )
 (prompt "\n\t\t现在请输入地面控制点")
 (prompt "\n\t\t*********************************************************")
 (setq n (getint "\n 地面控制点数: "))
 (prompt "\n -----*-----*-----")
 (setq i 1)
 (setq bg1 (getdist "\n 地面起点标高: "))
 (setq b1 nil)
 (while (< i n)
  (setq p1 (getpoint (strcat "\n < "(itoa (+ i 1))" >点(距离,标高): ")))
  (setq b1 (cons (list (+ i 1) p1) b1))
  (setq i (+ i 1))
 )
 (cons (list 1 (list 0.0 bg1)) (reverse b1))
)

(defun chx3 ( b )
 (prompt "\n\t\t现在请校对和修改")
 (prompt "\n\t***************************************************************")
 (setq n (length b))
 (setq i 0)
 (while (< i n)
  (setq jp1 (ntH i b))
  (setq jp nil)
  (setq p1 (getpoint (strcat " \n <"(itoa (car jp1)) " >点新值<"
   (rtos (car (cadr jp1)) 2 3) "," (rtos (cadr (cadr jp1)) 2 3)
  " >: ")))
  (IF (NULL P1) (SETQ P1 (CADR JP1)) (SETQ JP T))
  (if  JP         (setq b (subst (list (CAR JP1) P1) JP1 B)))
  (setq i (+ i 1))
 )
 b
)

(defun prt3 ( a )
 (setq n (length a))
 (princ "\n")  (princ "控制点") (princ "\t\t") (princ "水平距离")
    (princ "\t\t") (princ "地面标高")
 (setq i 0)
 (while (< i n)
  (princ "\n") (princ (car (nth i a))) (princ "\t\t")
   (princ (rtos (car (cadr (nth i a))) 2 3)) (princ "\t\t\t")
   (princ (rtos (cadr (cadr (nth i a))) 2 3))
  (setq i (+ i 1))
 )
)

(defun dm4 ( )
 (setq n (length a))
 (setq i 0)
 (setq ll (* k (apply '+ (mapcar 'car (mapcar 'cadr a)))))
 (if (= px "B") (setq pt0 (list (+ (car pd0) ll) (cadr pd0)))
                 (setq pt0 pd0))
 (setq m (car pt0))
 (setq b1 nil)
 (setq b2 nil)
 (setq h1 (apply 'min bgb3))
 (while (< i n)
  (setq p1 (cadr (nth i a)))
  (cond ((= px "F")
  (setq b1 (cons (+ m (* k (car p1))) b1))
  (setq m (+ m (* k (car p1))))))
  (cond ((= px "B")
  (setq b1 (cons (- m (* k (car p1))) b1))
  (setq m (- m (* k (car p1))))))
  (setq b2 (cons (+ (* 10.0 (- (cadr p1) h1)) (cadr pt0)) b2))
  (setq i (+ i 1))
 )
 (reverse (mapcar 'list b1 b2 ))
)

;***************************** PSGX ********************************
(defun pg1 ( )
 (prompt "\n\t\t现在请输入管道特征")
 (prompt "\n\t***************************************************************")
 (setq n (getint "\n 检查井数: "))
 (prompt "\n -----*-----*-----")
 (setq j1 (getstring t "\n 起始井位编号: "))
 (while (= j1 "")
  (setq j1 (getstring t "\n 不许空输入! 重输: ")))
 (setq j1 (strcase j1))
 (initget 1)
 (setq lch0 (getstring t "\n 起始井位里程<桩号><米>:"))
 (initget 1)
 (setq bg0 (getdist "\n 起始井底标高: "))
 (setq bg bg0)
 (setq i 2 jg "D200" cg "I" jp 0.0)
 (setq jb nil jlb nil lchb nil pjb nil bgb1 nil gjb nil gcb nil)
 (while (<= i n)
  (prompt "\n -----*-----*-----")
  (setq j2 (getstring t (strcat "\n < " (itoa i) " >井位编号: ")))
  (while (= j2 "")
  (setq j2 (getstring t "\n 不许空输入! 重输: ")))
  (initget 1)
  (setq jl (getdist "\n 距前井水平距离: "))

  (initget 1)
  (setq lch (getstring t "\n 该井位里程<桩号><米>:"))
  (setq lchb (cons lch lchb))

  (setq pj (getreal (strcat "\n 管道坡降< " (rtos jp 2 4) " >: ")))
  (if (= pj nil) (setq pj jp))
  (setq jp pj)
  (setq jlb (cons jl jlb) pjb (cons pj pjb))
  (setq bg2 (- bg (* jl pj)))
  (setq bg1 (getdist (strcat "\n 该井井底标高( " (rtos bg2 2 3)
            " ): "))) (if (= bg1 nil) (setq bg1 bg2))
  (setq bgb1 (cons bg1 bgb1)) (setq bg bg1)
  (setq gj (strcase (getstring t (strcat "\n 管径 < " jg " >: "))))
  (if (= gj "") (setq gj jg))
  (setq gc (getstring t (strcat "\n 管材;"
           "铸铁管I/钢筋混凝土管C< " cg " >: ")))
  (if (= gc "") (setq gc cg))
  (setq jg (strcase gj) cg (strcase gc))
  (setq gjb (cons (strcase gj) gjb) gcb (cons (strcase gc) gcb))
  (setq jb (cons (strcase j2) jb))
  (setq i (+ i 1))
 )
 (setq jb (reverse jb) lchb (reverse lchb) jlb (reverse jlb) pjb (reverse pjb) gjb
  (reverse gjb) gcb (reverse gcb) bgb1 (reverse bgb1))
)

(defun chx4 ( )
 (prompt "\n\t\t现在请校对和修改")
 (prompt "\n\t*************************************************************")
 (setq a1 j1 lch1 lch0 a2 bg0 b1 jb b2 jlb b3 pjb b4 bgb1 b5 gjb b6 gcb chbl lchb)
 (setq n (length b1))
 (setq j1 (strcase (getstring t (strcat "\n 起始井位编号< "
            a1 " >: "))))
 (if (= j1 "") (setq j1 a1))

 (initget 1)
 (setq lch0 (getstring (strcat "\n 起始井位里程<桩号><米><"lch1">:")))
 (if (= lch0 "") (setq lch0 lch1))

 (setq bg0 (getdist (strcat "\n 起始井井底标高<" (rtos a2 2
           3) " >: ")))
 (if (= bg0 nil) (setq bg0 a2 ))
 (setq bg bg0)
 (setq jb nil lchb nil jlb nil pjb nil bgb1 nil gjb nil gcb nil bgb2 nil)
 (setq i 0)
 (while (< i n)
  (prompt "\n -----*-----*-----")
  (setq j2 (strcase (getstring t (strcat "\n < " (itoa (+ i 2))
           " >井位编号< " (nth i b1) " >: "))))
  (if (= j2 "") (setq j2 (nth i b1)))
  (setq jb (cons j2 jb))
  (setq jl (getdist (strcat "\n 该井距前井水平距离< " (rtos (nth
           i b2 ) 2 3) " >: ")))
  (if (= jl nil) (setq jl (nth i b2)))
  (setq jlb (cons jl jlb)) 
  (setq lch (getstring t (strcat "\n 该井位里程<桩号><米><" 
                                 (nth i chbl) ">::")))
  (if (= lch "") (setq lch (nth i chbl)))
  (setq lchb (cons lch lchb))

  (setq pj (getreal (strcat "\n 管道坡降< " (rtos (nth i b3 )
           2 4) " >: ")))
  (if (= pj nil) (setq pj (nth i b3)))
  (setq pjb (cons pj pjb))
  (setq bg2 (- bg (* jl pj)))
  (setq bgb2 (cons bg2 bgb2))
  (setq bg1 (getdist (strcat "\n 该井井底标高< " (rtos (nth i
            b4) 2 3) " // " (rtos bg2 2 3) " >(Enter:默认旧值): ")))
  (if (= bg1 nil) (setq bg1 (nth i b4)))
  (setq bgb1 (cons bg1 bgb1))
  (setq bg bg1)
  (setq gj (strcase (getstring t (strcat "\n 管径< " (nth
           i b5 ) " >: "))))
  (if (= gj "") (setq gj (nth i b5)))
  (setq gjb (cons gj gjb))
  (setq gc (strcase (getstring t (strcat "\n 管材< " (nth
           i b6 ) " >: "))))
  (if (= gc "") (setq gc (nth i b6)))
  (setq gcb (cons gc gcb))
  (setq i (+ i 1))
 )
 (setq jb (reverse jb) lchb (reverse lchb) jlb (reverse jlb) pjb (reverse pjb) bgb1
          (reverse bgb1) gjb (reverse gjb) gcb (reverse gcb)
          bgb2 (reverse bgb2))
)

(defun prt4 ( )
 (setq jb1 (cons j1 jb))
 (setq bgb3 (cons bg0 bgb1))
 (setq lchb (cons lch0 lchb))
 (setq gdbz (mapcar 'list jb1 lchb (mapcar 'list (cons 0.0 jlb) bgb3)))
 (setq n (length jb))
 (princ "\n井号--井号") (princ "  水平距离")  
 (princ "  桩号--桩号") 
 (princ "  管道坡降") (princ "  起点标高") (princ "--")
 (princ "终点标高") (princ "  ") (princ "管径--管材")
 (setq i 0)
 (while (< i n)
  (princ "\n  ")  (princ (nth i jb1)) (princ "--") (princ (nth (+ i 1) jb1)) 
  (princ "    ")  (princ (rtos (nth i jlb) 2 3))  
  (princ "  ")  (princ (nth i lchb)) (princ "--") (princ (nth (1+ i) lchb))          
  (princ "  ")  (princ (rtos (nth i pjb) 2 3)) 
  (princ "    ") (princ (rtos (nth i bgb3) 2 3)) 
  (princ "--") (princ (rtos (nth i bgb2) 2 3)) 
  (princ "        ") (princ (nth i gjb)) 
  (princ "--") (princ (nth i gcb))
  (setq i (+ i 1))
 )
 (princ "\n最后井< ")  (princ (last jb1))  (princ ">") 
 (princ "\t 该井位桩号<米>:")  (princ (last lchb))
 (princ "\t 井底标高: ")  (princ (last bgb3))
)

(defun pg2 ( )
 (setq n (length jlb))
 (setq c (car pt0))
 (setq xzb nil )
 (setq i 0)
 (while (< i n)
  (setq jl (nth i jlb))
  (cond ((= px "B") (setq xzb (cons (- c (* k jl)) xzb))
         (setq c (- c (* k jl)))))
  (cond ((= px "F") (setq xzb (cons (+ c (* k jl)) xzb))
         (setq c (+ c (* k jl)))))
  (setq i (+ i 1))
 )
 (setq xzb (reverse xzb))
 (setq xzb (cons (car pt0) xzb))
 (setq minh (apply 'min bgb3))
 (setq n (length bgb3))
 (setq yzb nil)
 (setq i 0)
 (while (< i n)
  (setq yzb (cons (+ (* 10.0 (- (nth i bgb3) minh)) (cadr pt0))
                            yzb))
  (setq i (+ i 1))
 )
 (setq yzb (reverse yzb))
 (setq gdzb (mapcar 'list jb1 (mapcar 'list xzb yzb)))
)

(defun pg3 ( )
 (setq hh (mapcar 'car (dm4)))
 (cond ((= px "F")
 (setq h (reverse (cons (list (+ (car (last (dm4))) 15.0) 0.0)
                                      (reverse (dm4)))))))
 (cond ((= px "B")
 (setq h (reverse (cons (list 0.0 0.0) (reverse (dm4)))))))
 (setq maxh (+ 30.0 (apply 'max (mapcar 'cadr (dm4)))))
 (setq dmbg nil jd nil)
 (setq n (length gdzb))
 (setq i 0)
 (while (< i n)
  (setq l1 (nth i xzb))
  (setq ii 0)
  (setq d "t")
  (while d
   (setq l2 (nth ii hh))
   (cond ((= px "F")
   (if (> l2 l1) (setq d nil))))
   (cond ((= px "B")
   (if (< l2 l1) (setq d nil))))
   (if (= ii (1- n)) (setq d nil))
   (setq ii (+ ii 1))
  )
  (setq m (- (length hh) (length (member l2 hh))))
  (setq p1 (list l1 85.0))
  (setq p2 (list l1 (+ maxh 10.0)))
  (setq p3 (nth (- m 1) h))
  (setq p4 (nth m h))
  (if (inters p1 p2 p3 p4 nil) (setq pt p3))
  (if (inters p1 p2 p3 p4 t  ) (setq pt (inters p1 p2 p3 p4 nil)))
  (setq jd (cons pt jd))
  (setq dmbg (cons (+ (* 0.1 (- (cadr pt) (cadr pt0))) minh) dmbg))
  (setq  i (+ i 1))
 )
 (setq jd (reverse jd) dmbg (reverse dmbg))
 (setq n (length bgb2))
 (setq yzb2 nil)
 (setq i 0)
 (while (< i n)
  (setq bg (nth i bgb2))
  (setq yzb2 (cons (+ (* 10.0 (- bg minh)) (cadr pt0)) yzb2))
  (setq i (+ i 1))
 )
 (setq yzb2 (reverse yzb2))
 (setq gdzb2 (mapcar 'list (cdr xzb) yzb2))
 (setq js (mapcar '- dmbg bgb3))
)

;***************************** GDJC *****************************
(defun gdjc2 ()
 (prompt "\n\t\t现在请输入管道基础")
 (prompt "\n\t************************************************************")
 (prompt "\n\t\t键入:<E or e>退出输入")
 (setq j1 (strcase (getstring t " \n 起始井井位编号: ")))
 (setq gdjc nil)
 (setq d "t")
 (while d
  (while (= (assoc j1 gdbz) nil)
  (setq j1 (strcase (getstring t "\n 没有此井号! 重试: "))))
  (setq j2 (strcase (getstring t " \n 到井井位编号: ")))
  (while (= (assoc j2 gdbz) nil)
  (setq j2 (strcase (getstring t "\n 没有此井号! 重试: "))))
  (initget 1 "SO S 90C 135C 180C")
  (setq jc (getkword "\n 管道基础;/素土SO/砂土S/90度混凝土90C/135度混凝土135C/180度混凝土180C/: "))
  (setq gdjc (cons (list j1 j2 jc) gdjc))
  (prompt "\n -----*-----*-----")
  (setq j1 (strcase (getstring t " \n 起点井位编号<下段管道>: ")))
  (if (or (= j1 "e") (= j1 "E")) (setq d nil))
 )
 (setq gdjc (reverse gdjc))
)

;*************************** JCGD ***************************
(defun jcgd2 ()
 (prompt "\n\t\t现在请输入过路管道")
 (prompt "\n\t\t*************************************************************")
 (prompt "\n\t\t键入:<E or e>退出输入")

 (setq j (strcase (getstring t " \n 距离过路管道最近的前一井位编号: ")))
 (setq jcgd nil)
 (setq d "t")
 (while d
  (while (= (assoc j gdbz) nil)
  (setq j (strcase (getstring t " \n 没有此井号! 重试: "))))
  (initget 3)
  (setq jl (getdist " \n 过路管道到该井位水平距离<米>: "))
  (initget 1 "GS XH YS WS DL TX RQ")
  (setq nx (getkword
  "\n 管道类型:给水GS/循环XH/雨水YS/污水WS/动力DL/通信TX/燃气RQ: "))
  (setq nx (strcase nx))
  (cond ((= nx "GS" )(setq gj (getstring t " \n 管径<DN...>: "))
         (initget 1)
         (setq bg (getdist " \n 管中心标高<米>: ")))

        ((= nx "XH" )(setq gj (getstring t " \n 管径<DN...>: "))
         (initget 1)
         (setq bg (getdist " \n 管中心标高<米>: ")))

        ((= nx "YS" )(setq gj (getstring t " \n 管径<DN...>: "))
         (initget 1)
         (setq bg (getdist " \n 管内底标高<米>: ")))

        ((= nx "WS" )(setq gj (getstring t " \n 管径<DN...>: "))
         (initget 1)
         (setq bg (getdist " \n 管内底标高<米>: ")))

        ((= nx "DL" )(setq gj (getstring t " \n 管径<DN...>: "))
         (initget 1)
         (setq bg (getdist " \n 管外底标高<米>: ")))

        ((= nx "TX")(setq gj (getstring t  "\n 管径<DN...>: "))
         (initget 1)
         (setq bg (getdist " \n 管外底标高<米>: ")))

        ((= nx "RQ" )(setq gj (getstring t  "\n 管径<DN...>: "))
         (initget 1)
         (setq bg (getdist  "\n 管外底标高<米>: ")))
  )

  (initget 1)
  (setq glch (getstring t "\n 请输入该过路管道里程<桩号><米>: "))

  (setq jcgd (cons (list j jl nx (strcase gj) bg glch) jcgd))
  (prompt "\n -----*-----*-----")
  (setq j (strcase (getstring t " \n 下一根过路管道所距离的井位编号: ")))
  (if (or (= j "e") (= j "E")) (setq d nil))
 )
 (setq jcgd (reverse jcgd))
)

;****************************** DRAW ****************************
(defun hdmx2 ()
 (command "color" "3")
 (apply 'command (cons "line" (reverse (cons "" (reverse (dm4)
                 )))))
)
(defun hpgx ( )
 (command "color" "2")
 (cond ((= px "F")
 (command "line" (list (- (car (cadr (nth 0 gdzb))) 2.0) (-
          (cadr (cadr (nth 0 gdzb))) 0.5)) (list (- (car
          (nth 0 jd))  2.0) (cadr (nth 0 jd))) "")))
 (cond ((= px "B")
 (command "line" (list (+ (car (cadr (nth 0 gdzb))) 2.0) (-
          (cadr (cadr (nth 0 gdzb))) 0.5)) (list (+ (car
          (nth 0 jd))  2.0) (cadr (nth 0 jd))) "")))
 (setq n (length gdzb2))
 (setq i 0)
 (while (< i n)
  (setq p1 (cadr (nth i gdzb)))
  (setq p2 (cadr (nth (+ i 1) gdzb)))
  (setq jd1 (nth i jd))
  (setq jd2 (nth (+ i 1) jd))
  (setq p7 (nth i gdzb2))
  (cond ((= px "F")
  (setq pp1 (list (+ (car p1) 2.0) (cadr p1)))
  (setq pp2 (list (- (car p2) 2.0) (cadr p2)))
  (setq jj1 (list (+ (car jd1) 2.0) (cadr jd1)))
  (setq jj2 (list (- (car jd2) 2.0) (cadr jd2)))))
  (cond ((= px "B")
  (setq pp1 (list (- (car p1) 2.0) (cadr p1)))
  (setq pp2 (list (+ (car p2) 2.0) (cadr p2)))
  (setq jj1 (list (- (car jd1) 2.0) (cadr jd1)))
  (setq jj2 (list (+ (car jd2) 2.0) (cadr jd2)))))
  (setq p3 (inters p1 p7 pp1 jj1 nil))
  (setq p5 (inters p1 p7 pp2 jj2 nil))
  (setq gj (nth i gjb))
  (setq nn (strlen gj))
  (if (= (substr gj 2 1) "N") (setq cj (* 0.01 (atof (substr gj
    3 (- nn 2)))))  (setq cj (* 0.01 (atof (substr gj 2 (- nn
                                                    1))))))
  (setq p4 (list (car p3) (+ (cadr p3) cj)))
  (setq p6 (list (car p5) (+ (cadr p5) cj)))
  (command "color" "2")
  (cond ((= px "F")
  (command "line" (list (- (car jd1) 2.0) (cadr jd1)) jj1 p4 "")
  (command "line" (list (- (car p2) 2.0) (- (cadr p2) 0.5))
            p5 "")))
  (cond ((= px "B")
  (command "line" (list (+ (car jd1) 2.0) (cadr jd1)) jj1 p4 "")
  (command "line" (list (+ (car p2) 2.0) (- (cadr p2) 0.5))
            p5 "")))
  (command "line" p6 jj2 "")
  (command "color" "1")
  (command "pline" p3 "w" "0.8" "" p5 "")
  (command "pline" p4 p6 "")
  (command "color" "2")
  (command "pline" (list (- (car p1) 3.0) (- (cadr p1) 0.5))
           (list (+ (car p1) 3.0) (- (cadr p1) 0.5)) "")
  (setq i (+ i 1))
 )
 (command "pline" (list (- (car p2) 3.0) (- (cadr p2) 0.5))
                  (list (+ (car p2) 3.0) (- (cadr p2) 0.5)) "")
 (command "color" "2")
 (cond ((= px "F")
 (command "line" jj2 (list (+ (car jj2) 4.0) (cadr jj2))
                (list (+ (car p2) 2.0) (- (cadr p2) 0.5)) "")))
 (cond ((= px "B")
 (command "line" jj2 (list (- (car jj2) 4.0) (cadr jj2))
                (list (- (car p2) 2.0) (- (cadr p2) 0.5)) "")))
)

(defun hcx2 ( )
 (setq n (length xzb))
 (setq gjjb (reverse (cons (last gjb) (reverse gjb))))
 
 (setq msb01 nil)
 (setq i 0)
 (while (< i (1- n))
   (setq a01 (nth (1+ i) dmbg))
   (setq b01 (nth i bgb2))
   (setq c01 (- a01 b01))
   (setq msb01 (cons c01 msb01))
   (setq i (1+ i))
 )
 (setq msb01 (reverse msb01))

 (setq i 0)
 (while (< i n)
  (setq p1 (nth i jd))
  (if (or (= i 0) (= i (- n 1))) 
      (progn
        (setq p2 (list (car p1) 65.0))
        (command "color" "2")
        (command "line" p1 p2 "")
      )
      (progn
        (setq p3 (list (car p1) 130.0))
        (setq p4 (list (car p1) 122.5))
        (setq p2 (list (car p1) 100.0))
        (command "color" "2")
        (command "line" p1 p3 "")
        (command "line" p4 p2 "")
      )
  )
  (setq i (+ i 1))
 )

 (setq i 0)
 (while (< i n)
  (setq gj (nth i gjjb))
  (setq dn (strlen gj))
  (if (= (substr gj 2 1) "N") (setq gjj (read (substr gj 3 (- dn 2))))
      (setq gjj (read (substr gj 2 (- dn 1)))))

;;  (if (and (>= gjj 200.0) (<= gjj 600.0))
;;      (if (and (<= gjj 400.0) (<= (nth i js) (+ 1.0 (* gjj 0.001))))
;;             (setq jj "%%c700") (setq jj "%%c1000"))
;;                )

  (if (and (>= gjj 200.0) (< gjj 600.0)) (setq jj "%%c1000"))

  (if (and (>= gjj 600.0) (< gjj 800.0)) (setq jj "%%c1250"))
  (if (and (>= gjj 800.0) (< gjj 1000.)) (setq jj "%%c1500"))
  (if (and (>= gjj 1000.0) (< gjj 1200.0)) (setq jj "%%c2000"))
  (if (and (>= gjj 1200.0) (< gjj 1500.0)) (setq jj "%%c2500"))
;;  (command "color" "2")
;;  (if (or (= i 0) (= i (- n 1))) (command "line" (list (nth
;;      i xzb) 65.0) (nth i jd) "") (command "line" (list (nth
;;      i xzb) 85.0) (nth i jd) ""))
  (command "color" "1")
  (cond ((= px "F")
  (if (= i 0)
  (command "text"     (list (+ (nth i xzb) 1.0) 78.0) "2.5" "0"
                      (nth i jb1)))
  (if (= i (1- n))
  (command "text" "r" (list (- (nth i xzb) 1.0) 78.0) "2.5" "0"
                      (nth i jb1))
                      )
  (if (and (/= i 0) (/= i (1- n)))
  (command "text" "c" (list (+ (nth i xzb) 1.0) 78.0) "2.5" "0"
                      (nth i jb1))
                      )
                                  
  (command "text" (list (+ (nth i xzb) 4.0) 163.5) "2.5" "90"
                  (rtos (nth i dmbg) 2 2))
  (command "text" (list (+ (nth i xzb) 4.0) 179.0) "2.5" "90"
                  (nth i lchb))
  (command "text" (list (+ (nth i xzb) 4.0) 147.5) "2.5" "90"
                  (rtos (nth i bgb3) 2 2))
  (command "text" (list (+ (nth i xzb) 4.0) 134.5) "2.5" "90" (rtos
          (nth i js) 2 2))

  (if (= i 0)
  (command "text"     (list (+ (nth i xzb) 1.0) 68.75) "2.5" "0"
                      jj ))
  (if (= i (1- n))
  (command "text" "r" (list (- (nth i xzb) 1.0) 68.75) "2.5" "0"
                      jj ))
  (if (and (/= i 0) (/= i (1- n)))
  (command "text" "c" (list (+ (nth i xzb) 1.0) 68.75) "2.5" "0"
                      jj ))
                      ))

;;  (command "text" (list (+ (nth i xzb) 4.0) 70.0) "2.5" "0" jj)))

  (cond ((= px "B")

  (if (= i 0)
  (command "text" "r" (list (- (nth i xzb) 1.0) 78.0) "2.5" "0"
                      (nth i jb1)))
  (if (= i (1- n))
  (command "text"  (list (+ (nth i xzb) 1.0) 78.0) "2.5" "0"
                      (nth i jb1))
                      )
  (if (and (/= i 0) (/= i (1- n)))
  (command "text" "c" (list (+ (nth i xzb) 1.0) 78.0) "2.5" "0"
                      (nth i jb1))
                      )

  (command "text" (list (- (nth i xzb) 1.0) 163.5) "2.5" "90"
                  (rtos (nth i dmbg) 2 2))
  (command "text" (list (+ (nth i xzb) 4.0) 179.0) "2.5" "90"
                  (nth i lchb))
  (command "text" (list (- (nth i xzb) 1.0) 147.5) "2.5" "90"
                  (rtos (nth i bgb3) 2 2))
  (command "text" (list (- (nth i xzb) 1.0) 134.5) "2.5" "90" (rtos
         (nth i js) 2 2))


  (if (= i 0)
  (command "text" "r"  (list (- (nth i xzb) 1.0) 68.75) "2.5" "0"
                      jj ))
  (if (= i (1- n))
  (command "text" (list (+ (nth i xzb) 1.0) 68.75) "2.5" "0"
                      jj ))
  (if (and (/= i 0) (/= i (1- n)))
  (command "text" "c" (list (+ (nth i xzb) 1.0) 68.75) "2.5" "0"
                      jj ))
                      ))
  
  (setq i (+ i 1))
 )

 (setq n (length jlb))
 (setq i 0)
 (while (< i (1- n))
  (cond ((= px "F")
    (command "text" (list (- (car (nth i gdzb2)) 1.0) 147.5) "2.5"
                    "90" (rtos (nth i bgb2) 2 2))
    (command "text" (list (- (car (nth i gdzb2)) 1.0) 134.5) "2.5"
                    "90" (rtos (nth i msb01) 2 2))
        )
  )
  (cond ((= px "B")
    (command "text" (list (+ (car (nth i gdzb2)) 4.0) 147.5) "2.5"
                    "90" (rtos (nth i bgb2) 2 2))
    (command "text" (list (+ (car (nth i gdzb2)) 4.0) 134.5) "2.5"
                    "90" (rtos (nth i msb01) 2 2))
        )
  )
  (setq i (+ i 1))
 )

 (setq n (length jlb))
 (setq i 0)
 (while (< i n)
    (progn 
      (command "text" "c" (list (* 0.5 (+ (car (cadr (nth i gdzb)))
               (car (cadr (nth (+ i 1) gdzb))))) 106.0) "2.5" "0"
                       (rtos (nth i jlb) 2 2))
      (command "text" "c" (list (* 0.5 (+ (car (cadr (nth i gdzb)))
               (car (cadr (nth (+ i 1) gdzb))))) 117.5) "2.5" "0"
                       (rtos (* (nth i pjb) 1000.0) 2 3))
      (setq i (1+ i))
    )
 )
)

(defun hgdjc2 ()
 (setq n (length gdjc))
 (setq i 0)
 (while (< i n)
  (setq j1 (nth 0 (nth i gdjc)) j2 (nth 1 (nth i gdjc)))
  (setq p1 (list (* 0.5 (+ (car (cadr (assoc j1 gdzb))) (car (
           cadr (assoc j2 gdzb))))) 67.0 ))
  (setq cj (nth 2 (nth i gdjc)))
  (cond ((= cj "SO") (setq jc "素土基础"))
        ((= cj "S") (setq jc "砂垫层基础"))
        ((= cj "90C") (setq jc "90%%d混凝土基础"))
        ((= cj "135C") (setq jc "135%%d混凝土基础"))
        ((= cj "180C") (setq jc "180%%d混凝土基础"))
  )
  (command "color" "1")
  (command "text" "c" p1 "5" "0" jc)
  (command "color" "2")
  (command "line" (list (car (cadr (assoc j2 gdzb))) 65.0)
         (list (car (cadr (assoc j2 gdzb)))  75.0) "")
  (setq i (+ i 1))
 )
)

(defun hgjgc2 ( )
 (if (and (apply '= gjb) (apply '= gcb)) (setq w "y1")
     (setq w "y2")) (command "color" "1")
 (cond ((= w "y1")
        (if (= (nth 0 gcb) "I") (setq gc "排水铸铁管"))
        (if (= (nth 0 gcb) "C") (setq gc "钢筋混凝土管"))
        (setq pt (list (* 0.5 (+ (car (nth 0 jd)) (car (last jd))))
        124.25)) 
        (command "text" "r" (list (- (car pt) 1.0) 124.25) "3.5"
        "0" (nth 0 gjb)) 
        (command "text" pt "5" "0" gc))
 )
 (cond ((= w "y2")
 (setq n (length gjb))
 (setq gj0 (nth 0 gjb))
 (setq gc0 (nth 0 gcb))
 (setq j1 (nth 0 jb1))
 (setq i 0)
 (while (< i n)
  (if (= gc0 "I") (setq gc "排水铸铁管"))
  (if (= gc0 "C") (setq gc "钢筋混凝土管"))
  (cond ((or (/= (nth i gjb) gj0) (/= (nth i gcb) gc0))
         (setq j2 (nth i jb1)) (setq pt (list (* 0.5 (+ (car (cadr
         (assoc j1 gdzb))) (car (cadr (assoc j2 gdzb))))) 124.25))
         (command "color" "1")
         (command "text" "r" (list (- (car pt) 1.0) 124.25) "3.5"
         "0" gj0) 
         (command "text" pt "5" "0" gc)
         (command "color" "2")
         (command "line" (list (car (cadr (assoc j2 gdzb))) 122.5)
         (list (car (cadr (assoc j2 gdzb))) 130.0) "")
         (setq gj0 (nth i gjb)) (setq gc0 (nth i gcb)) (setq j1 j2)
  ))
  (setq i (+ i 1))
 )
 (if (= (last gcb) "I") (setq gc "排水铸铁管"))
 (if (= (last gcb) "C") (setq gc "钢筋混凝土管"))
 (setq pt (list (* 0.5 (+ (car (cadr (assoc j2 gdzb))) (car (cadr
          (last gdzb))))) 124.25))
 (command "color" "1")
 (command "text" "r" (list (- (car pt) 1.0) 124.25) "3.5" "0" gj0)
 (command "text" pt "5" "0" gc)))
)

(defun hbg2 ()
 (setq minb (fix   (- minh 3.0)))
  (setq p3 (list 124.0 (+ (* 10.0 (- minb minh)) (cadr pt0))))
  (setq d "t" c 0.0)
  (while d
   (setq p1 (list 124.0 (+ c (cadr p3))))
   (setq p2 (list 124.0 (+ 10.0 (cadr p1))))
   (command "color" "3")
   (command "pline" p1 "w" "2.0" "" p2 "")
   (setq c (+ c 20.0))
   (if (> c (- maxh (cadr p3))) (setq d nil))
  )
  (setq p4 p2)
  (command "line" (list 125.0 (cadr p3)) (list 125.0 (cadr p4))
   (list 123.0 (cadr p4)) (list 123.0 (cadr p3)) "c" )
  (setq n (fix (* 0.1 (- (cadr p4) (cadr p3)))))
  (setq c 0.0)
  (setq i 0)
  (while (< i (+ n 1))
   (setq p5 (list 121.5 (+ c (cadr p3))))
   (command "color" "1")
   (command "text" "r" p5 "2.5" "0" (rtos (+ minb i) 2 2))
   (setq c (+ c 10.0))
   (setq i (+ i 1))
  )
)

(defun hjcgd2 ()
 (SETVAR "DIMEXO" 3.0)
 (SETVAR "DIMEXE" 3.0)
 (setvar "DIMTSZ" 0)
 (setvar "DIMTXT" 2.50)
 (setvar "DIMASZ" 1)
;; (command "dim" "dimblk" "xx0" "exit")
;; (setvar "DIMTAD" 1)
 (setq n (length jcgd))
 (setq i 0)
 (while (< i n)
  (setq jcd (nth i jcgd))
  (setq j (nth 0 jcd) jl (nth 1 jcd) nx (nth 2 jcd) 
        gj (nth 3 jcd) bg (nth 4 jcd) glch (nth 5 jcd))

  (cond ((= px "F")  
         (setq p1 (list (+ (car (cadr (assoc j gdzb))) (* k jl)) 
         (+ (* 10.0 (- bg minh)) (cadr pt0))))
        )
        ((= px "B")
         (setq p1 (list (- (car (cadr (assoc j gdzb))) (* k jl)) 
         (+ (* 10.0 (- bg minh)) (cadr pt0))))
        )
  )

  (setq nn (strlen gj) )
  (if (= (substr  gj 2 1) "N") (setq cj (* 0.001   (atof (substr
   gj 3 (- nn 2))))) (setq cj (* 0.001   (atof (substr gj 2 (- nn
   1))))))
  (command "color" "4")
  (cond ((= nx "GS" ) (command "ellipse" "c" p1 (list (+ (car p1)
        (* 2.5 cj)) (cadr p1)) (* 5.0 cj)) 
        (command "color" "6")                    
        (command "text" (list (- (car p1) 1.0) 206.0) "3.5" "90" 
        "给水管道 管径")
        (command "insert" "c:/jiangdh/tl/bgfh1"
                (list (+ (+ (car p1) (* 2.5 cj)) 4.02) (cadr p1)) 
                "0.01" "0.01" "")
        (setq pta (list (car p1) (+ (cadr p1) (* 5.0 cj))))
        (command "color" "white")
        (command "text"  
                (list (+ (+ (car p1) (* 2.5 cj)) 4.02) (+ (cadr p1) 2.8))
                "2.5" "0" (rtos bg 2 2)))

        ((= nx "WS") (command "ellipse" p1 (list (car p1) (+ (
        cadr p1) (* 10.0 cj))) (* 2.5 cj)) 
        (command "color" "6")              
        (command "text" (list (- (car p1) 1.0) 206.0) "3.5" "90" 
        "污水管道 管径 ")
        (command "insert" "c:/jiangdh/tl/bgfh1" 
                (list (+ (car p1) 3.88) (cadr p1)) "0.01" "0.01" "")
        (setq pta (list (car p1) (+ (cadr p1) (* 10.0 cj))))
        (command "color" "white")
        (command "text"  
                (list (+ (car p1) 3.88) (+ (cadr p1) 2.8))
                "2.5" "0" (rtos bg 2 2)))
                        
        ((= nx "XH" ) (command "ellipse" "c" p1 (list (+ (car p1)
        (* 2.5 cj)) (cadr p1)) (* 5.0 cj)) 
        (command "color" "6")                    
        (command "text" (list (- (car p1) 1.0) 206.0) "3.5" "90" 
        "循环水管道 管径")
        (command "insert" "c:/jiangdh/tl/bgfh1"
                (list (+ (+ (car p1) (* 2.5 cj)) 4.02) (cadr p1)) 
                "0.01" "0.01" "")
        (setq pta (list (car p1) (+ (cadr p1) (* 5.0 cj))))
        (command "color" "white")
        (command "text"  
                (list (+ (+ (car p1) (* 2.5 cj)) 4.02) (+ (cadr p1) 2.8))
                "2.5" "0" (rtos bg 2 2)))

        ((= nx "YS" ) (command "ellipse" p1 
        (list (car p1) (+ (cadr p1) (* 10.0 cj))) (* 2.5 cj)) 
        (command "color" "6")                 
        (command "text" (list (- (car p1) 1.0) 206.0) "3.5" "90" 
        "雨水管道 管径")
        (command "insert" "c:/jiangdh/tl/bgfh1" 
                (list (+ (car p1) 3.88) (cadr p1)) "0.01" "0.01" "")
        (setq pta (list (car p1) (+ (cadr p1) (* 10.0 cj))))
        (command "color" "white")
        (command "text"  
                (list (+ (car p1) 3.88) (+ (cadr p1) 2.8))
                "2.5" "0" (rtos bg 2 2)))

        ((= nx "DL" ) (command "ellipse" p1 
        (list (car p1) (+ (cadr p1) (* 10.0 cj))) (* 2.5 cj)) 
        (command "color" "6")                 
        (command "text" (list (- (car p1) 1.0) 206.0) "3.5" "90" 
        "动力管道 管径")
        (command "insert" "c:/jiangdh/tl/bgfh1" 
                (list (+ (car p1) 3.88) (cadr p1)) "0.01" "0.01" "")
        (setq pta (list (car p1) (+ (cadr p1) (* 10.0 cj))))
        (command "color" "white")
        (command "text"  
                (list (+ (car p1) 3.88) (+ (cadr p1) 2.8))
                "2.5" "0" (rtos bg 2 2)))
        
        ((= nx "RQ" ) (command "ellipse" p1 
        (list (car p1) (+ (cadr p1) (* 10.0 cj))) (* 2.5 cj)) 
        (command "color" "6")                 
        (command "text" (list (- (car p1) 1.0) 206.0) "3.5" "90" 
        "燃气管道 管径")
        (command "insert" "c:/jiangdh/tl/bgfh1" 
                (list (+ (car p1) 3.88) (cadr p1)) "0.01" "0.01" "")
        (setq pta (list (car p1) (+ (cadr p1) (* 10.0 cj))))
        (command "color" "white")
        (command "text"  
                (list (+ (car p1) 3.88) (+ (cadr p1) 2.8))
                "2.5" "0" (rtos bg 2 2)))
        
        ((= nx "TX" ) (command "ellipse" p1 
        (list (car p1) (+ (cadr p1) (* 10.0 cj))) (* 2.5 cj)) 
        (command "color" "6")                 
        (command "text" (list (- (car p1) 1.0) 206.0) "3.5" "90" 
        "通信管道 管径")
        (command "insert" "c:/jiangdh/tl/bgfh1" 
                (list (+ (car p1) 3.88) (cadr p1)) "0.01" "0.01" "")
        (setq pta (list (car p1) (+ (cadr p1) (* 10.0 cj))))
        (command "color" "white")
        (command "text"  
                (list (+ (car p1) 3.88) (+ (cadr p1) 2.8))
                "2.5" "0" (rtos bg 2 2)))
  )

  (command "color" "6")
;;  (command "line" (list (car p1) ( + (cadr p1) (* cj 0.5))) (list (car p1
;;                 ) 175.0) "")
  (command "line" pta (list (car p1) 175.0) "")
  (command "text" (list (- (car p1) 1.0) 231.5) "2.5" "90" gj)
  (command "text" (list (- (car p1) 1.0) 179.0) "2.5" "90" glch)
;; (command "text" (list (- (car p1) 1.0) 246.0) "2.5" "90" (rtos
;;                                                    bg 2 3))
;;  (command "dim1" "hor" (list (car p1) (- (cadr p1) 10.0)) (list
;;   (- (car p1) (* k jl)) (- (cadr p1) 10.0)) (list (car p1) (- (
;;   cadr p1) 10.0)) (rtos (abs jl) 2 3))
  (setq i (+ i 1))
 )
)

(defun c:psdat ( )
 (textscr)
 (setq jk (getvar "DWGNAME"))
 (setq sjk (getstring t (strcat "建立数据文件< " jk " >: ")))
 (if (= sjk "") (setq sjk jk)) (setq sj sjk)
 (setq b (dm3))
 (setq a (chx3 b))
 (prt3 a) (princ)
 (initget 1 "Y N")
 (setq xg (getkword "\n 需要修改吗? (Y/N): "))
 (while (= xg "Y")
  (setq b a) (setq a (chx3 b)) (prt3 a) (princ)
  (initget 1 "Y N")
  (setq xg (getkword "\n 再需要修改吗? (Y/N): ")))
 (setq sjk (open (strcat sj ".dat") "w"))
 (write-line "ground-control-points" sjk)
 (write-line "No:__Dist__Elev" sjk)
 (setq n (length a))
 (setq i 0)
 (while (< i n)
  (write-line (strcat (itoa (+ i 1)) "__" (rtos (car (cadr (nth i a
    ))) 2 2) "__" (rtos (cadr (cadr (nth i a))) 2 2)) sjk)
  (setq i (+ i 1))
 )
 (close sjk)
 (pg1) (chx4) (prt4)
 (initget 1 "Y N")
 (setq xg (getkword "\n 需要修改吗? (Y/N): "))
 (while (= xg "Y")
  (chx4) (prt4)
  (initget 1 "Y N")
  (setq xg (getkword "\n 再需要修改吗? (Y/N): ")))
 (setq sjk (open (strcat sj ".dat") "a"))
 (write-line "control-points-pipeline" sjk)
 (write-line "No:__ToNo:__Meters__ToMeters__Dist__Slope__Elev1__Elev2__Diameter__Material" sjk)
 (setq n (length jlb))
 (setq i 0)
 (while (< i n)
  (write-line (strcat (nth i jb1) "__" (nth (+ i 1) jb1) "__"
            (nth i lchb) "__" (nth (+ i 1) lchb) "__" 
        (rtos (nth i jlb) 2 2) "__" (rtos (nth i pjb) 2 4) "__"
        (rtos (nth i bgb3) 2 2) "__" (rtos (nth i bgb2) 2 2) "__"
        (nth i gjb) "__" (nth i gcb)) sjk)
  (setq i (+ i 1))
 )
 (write-line "endpoint" sjk)
 (write-line "No:__Meters__Elev1" sjk)
 (write-line (strcat (last jb1) "__" 
             (last lchb) "__" (rtos (last bgb3) 2 2)) sjk)
 (close sjk)
 (gdjc2)
 (setq sjk (open (strcat sj ".dat") "a"))
 (write-line "base-pipeline" sjk)
 (write-line "No:__ToNo:__Base" sjk)
 (setq n (length gdjc))
 (setq i 0)
 (while (< i n)
  (write-line (strcat (car (nth i gdjc)) "__" (cadr (nth i gdjc))
        "__" (last (nth i gdjc))) sjk)
  (setq i (+ i 1))
 )
  (write-line "cross-points" sjk)
  (write-line "No:__Dist__Type__Diameter__Elev__Meters" sjk)
 (close sjk)
 (initget 1 "Y N")
 (setq jc (getkword "\n 需要画过路管吗? (Y/N): "))
 (cond ((= jc "Y") (jcgd2)
  (setq sjk (open (strcat sj ".dat") "a"))
  (setq n (length jcgd))
  (setq i 0)
  (while (< i n)
   (write-line (strcat (car (nth i jcgd)) "__"
        (rtos (nth 1 (nth i jcgd)) 2 2) "__" (nth 2 (nth
        i jcgd)) "__" (nth 3 (nth i jcgd)) "__" (rtos (nth 4
        (nth i jcgd)) 2 2) "__" (nth 5 (nth I jcgd))) sjk)
   (setq i (+ i 1))
  )
  (close sjk)))
 (setq sjk (open (strcat sj ".dat") "a"))
 (write-line "input-end" sjk)
 (close sjk)
)

(defun ss (ws)
 (setq n (strlen ws))
 (setq i 2) (setq ii 1)
 (setq kk2 nil)
 (while (<= i n)
  (setq kk1 (substr ws i 1)) (setq kk0 (substr ws (- i 1) 1))
  (cond ((and (= kk1 "_") (/= kk0 "_"))
        (setq mm (substr ws ii (- i ii)))
        (setq kk2 (cons mm kk2))
        (setq ii (+ i 2))
  ))
  (setq i (+ i 1))
 )
 (setq kk2 (cons (substr ws ii (- (+ i 1) ii)) kk2))
 (reverse kk2)
)

(defun c:poutdat ()

 (setq jk (getvar "DWGNAME"))
 (setq sj (getstring t (strcat "\n 读取数据文件< " jk " >: ")))
 (if (= sj "") (setq sj jk))
 (setq sjk (open (strcat sj ".dat") "r"))
 (setq a nil jb1 nil lchb nil jlb nil pjb nil bgb2 nil bgb3 nil gjb nil
         bgb nil bb1 nil cc1 nil gcb nil gdjc nil jcgd nil)
 (setq d "t")
 (while d
  (setq sj (read-line sjk)) (setq ks (ss sj))
   (cond ((= sj "ground-control-points") (setq js "h1")))
   (cond ((= sj "control-points-pipeline") (setq js "h2")))
   (cond ((= sj "endpoint") (setq js "h3")))
   (cond ((= sj "base-pipeline") (setq js "h4")))
   (cond ((= sj "cross-points") (setq js "h5")))
   (cond ((= sj "input-end") (setq js "h6")))
   (cond ((= js "h1") (if (or (= sj "ground-control-points")
         (= sj "No:__Dist__Elev")) (setq yy "z1") (setq yy "z2"))
            (if (= yy "z2") (setq a (cons (list (read (car ks))
          (list (read (nth 1 ks)) (read (last ks)))) a)))
            ))
   (cond ((= js "h2") (if (or (= sj "control-points-pipeline") (= sj
         "No:__ToNo:__Meters__ToMeters__Dist__Slope__Elev1__Elev2__Diameter__Material"))
            (setq yy "z1") (setq yy "z2"))
            (cond ((= yy "z2") 
                   (setq jb1 (cons (car ks) jb1))
                   (setq lchb (cons (nth 2 ks) lchb))
                   (setq jlb (cons (read (nth 4 ks)) jlb)) 
                   (setq pjb (cons (read (nth 5 ks)) pjb))
                   (setq bgb3 (cons (read (nth 6 ks)) bgb3)) 
                   (setq bgb2 (cons (read (nth 7 ks)) bgb2)) 
                   (setq gjb (cons (nth 8 ks) gjb))
                   (setq gcb (cons (last ks) gcb))))
                  )
            )
   (cond ((= js "h3") (if (or (= js "endpoint") (= js "No:__Meters__Elev1"))
         (setq vv "z1") (setq vv "z2"))
         (cond ((= vv "z2") 
                (setq bb1 (cons (car ks) bb1))
                (setq cc1 (cons (nth 1 ks) cc1))
                (setq bgb (cons (read (last ks)) bgb))))
               ))
   (cond ((= js "h4") (if (or (= sj "base-pipeline") (= sj
         "No:__ToNo:__Base")) (setq yy "z1") (setq yy "z2"))
         (cond ((= yy "z2") (setq gdjc (cons ks gdjc))))
            ))
   (cond ((= js "h5") (if (or (= sj "cross-points") (= sj
         "No:__Dist__Type__Diameter__Elev__Meters")) (setq yy "z1")
         (setq yy "z2"))
            (cond ((= yy "z2") (setq jcgd (cons (list (car ks) (read
         (nth 1 ks)) (nth 2 ks) (nth 3 ks) (read (nth 4 ks)) (last ks)) jcgd))))
            ))
   (cond ((= js "h6") (close sjk) (setq d nil)))
 )
 (setq a (reverse a) 
      jb1 (reverse (cons (car bb1) jb1)) 
      lchb (reverse (cons (car cc1) lchb)) 
      jlb (reverse jlb) pjb (reverse pjb)
      bgb3 (reverse (cons (car bgb) bgb3)) 
      bgb2 (reverse bgb2) gjb (reverse gjb) 
      gcb (reverse gcb) gdjc (reverse gdjc) jcgd (reverse jcgd))
 (setq jb (cdr jb1) bgb1 (cdr bgb3))
)

(defun c:hgdjc ()
 (gdjc2) (hgdjc2))

(defun c:hjcgd ()
 (jcgd2) (hjcgd2))

(defun c:pspm  ()
 (command "style" "standard" "romans,hztxt" "" "" "" "" "" "")
 (prompt   "\n\t\t绘制排水纵断面图")
 (prompt "\n\t**************************************************************")
 (prompt "\n\t~~~~~~~~~~~~~~~~~~~~~~~~~~~~~~~~~~~~~~~~~~~~~~~~~~~~~~~~~~~~~")
 (textscr)
 (setvar "BLIPMODE" 0) (c:poutdat)
 (setq bl (getreal "\n 输入绘图纵向比例(1000,500...): "))
 (setq bl00 (rtos bl 2 2))
          (setq k (/ 1000.0 bl))
 (initget 1 "F B")
 (setq px (getkword "\n 管道坡向;/正向(\)F/反向(/)B: "))
 (setq pd0 (getpoint "\n 管道起点座标(135,280): "))
  (if (= pd0 nil) (setq pd0 '(135 280)))
 (c:tk2) (dm4) (pg2) (pg3)
 (hdmx2) (hpgx) (hcx2) (hgjgc2) 
;; (hgdjc2) 
 (nk2) 
 (hbg2)
 (if (= bl00 "1000.00") 
     (command "insert" "c:/jiangdh/tl/bl1" '(62 222) "" "" "")
 )
 (if (= bl00 "500.00")
     (command "insert" "c:/jiangdh/tl/bl5" '(62 222) "" "" "")
 )
 (if (= bl00 "1000") 
     (command "insert" "c:/jiangdh/tl/bl1" '(62 222) "" "" "")
 )
 (if (= bl00 "500")
     (command "insert" "c:/jiangdh/tl/bl5" '(62 222) "" "" "")
 )
 (if (/= jcgd nil) (hjcgd2)))

(defun c:pspm2 ()
 (textscr)
 (prompt "\n\t\t局部绘制排水纵断面图")
 (prompt "\n\t\t***********************************************************")
 (C:POUTDAT)
 (setq bl (getreal "\n 输入绘图纵向比例(1000,500...): "))
      (setq k (/ 1000.0 bl))
 (initget 1 "F B")
 (setq px (getkword "\n 管道坡向;/正向(\)F/反向(/)B: "))
 (setq pd0 (getpoint "\n 管道起点座标(135,280): "))
 (if (= pd0 nil) (setq pd0 '(135 280))) (dm4)
 (if (= px "F") (setq pty (last (dm4))) (setq pty (car (dm4))))
  (command "move" "w" '(60.0 50.0) (list (- cd 20.0) (- kd 15.0)) ""
           '(0.0 0.0) (list (car pty) 0.0))
  (pg2) (pg3) (hdmx2) (hpgx) (hcx2) (hgjgc2) (hgdjc2) (nk2) (hbg2)
  (if (/= jcgd nil) (hjcgd2))
)


(textscr)
(princ "\n\n\t  排水纵断程序已加载，作者：张健君等。\n")
(princ "\n\t  启动命令：\n")
(princ "\n\t  建立数据文件：PSDAT")
(princ "\n\t  绘图命令：PSPM。\n")
(princ)











�

(defun c:redim ()
(setq sc2 (getvar "dimscale"))
(setq sc (/ sc2 sc1))
(setq a (ssget "x" (list (cons 0 "DIMENSION"))))
(setq b (sslength a))
(setq d 0)
(repeat b
(setq c (ssname a d))
(setq q (entget c))
(setq ea (assoc 10 (entget c)))
(setq e1 (cdr ea))
(setq x1 (car e1) y1 (cadr e1))
(setq eb (assoc 13 (entget c)))
(setq e2 (cdr eb))
(setq x2 (car e2) y2 (cadr e2))
(setq ec (assoc 14 (entget c)))
(setq e3 (cdr ec))
(setq x3 (car e3) y3 (cadr e3))
(if (= x1 x2)
(progn
(setq ll (abs (- y1 y2)))
(if (= ll 0) (setq ll 1))
(setq l (/ (- y1 y2) ll ))
(setq lst (cons 10 (subst (+ y2 (* ll l sc)) y1 e1)))
(setq ls (subst (cons 10 (cdr lst)) ea q))
(entmod ls)
))
(if (= x1 x3)
(progn
(setq ll (abs (- y1 y3)))
(if (= ll 0) (setq ll 1))
(setq l (/ (- y1 y3) ll ))
(setq lst (cons 10 (subst (+ y3 (* ll l sc)) y1 e1)))
(setq ls (subst (cons 10 (cdr lst)) ea q))
(entmod ls)
))
(if (= y1 y2)
(progn
(setq ll (abs (- x1 x2)))
(if (= ll 0) (setq ll 1))
(setq l (/ (- x1 x2) ll ))
(setq lst (cons 10 (subst (+ x2 (* ll l sc)) x1 e1)))
(setq ls (subst (cons 10 (cdr lst)) ea q))
(entmod ls)
))
(if (= y1 y3)
(progn
(setq ll (abs (- x1 x3)))
(if (= ll 0) (setq ll 1))
(setq l (/ (- x1 x3) ll ))
(setq lst (cons 10 (subst (+ x3 (* ll l sc)) x1 e1)))
(setq ls (subst (cons 10 (cdr lst)) ea q))
(entmod ls)
))
(setq d (+ d 1))
)
(princ))

(DEFUN C:ROTACOPY ()
(PROMPT "SELECT SUOBJECT")
(SETQ SUB (SSGET))
(SETQ POINT (GETPOINT "BASE POINT : "))
(SETQ ANGE (GETANGLE "ROTATE ANGLE = "))
(SETQ ANG (ATOF (ANGTOS ANGE 0 2)))
(WHILE (/= ANG 0)
(COMMAND "ARRAY" SUB "" "P" POINT "2" ANG "")
(SETQ ANGE (GETANGLE "ROTATE ANGLE = "))
(SETQ AN (ATOF (ANGTOS ANGE 0 2 )))
(SETQ ANG (+ ANG AN))
))

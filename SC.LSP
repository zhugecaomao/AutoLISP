(VMON)
defun c:SC
;(IF (= (TYPE F1) 'FILE ) "YES"  (STOP))
;(IF (= (TYPE F2) 'FILE ) "YES" (STOP))
(SETQ W1 P1)
;(command "vslide" "UJMBASE")
(SETQ BNAME (GETINT "\nInput basename:"))
(setq o (getreal "\nEnter [A] size:"))
(setq P (getreal "\nEnter [B] size:"))
(setq Q (getreal "\nEnter [C] size:"))
(SETQ P1 (GETPOINT "\nInsert Point:"))
(SETQ W1 P1)
;(command "vslide" "UJMBASE")
(SETQ BNAME (ITOA BNAME))
(SETQ B (SUBSTR  BNAME 1 2))
(SETQ E (SUBSTR  BNAME 3 2))
;HERE
(SETQ B (STRCAT B "0"))
(SETQ E (STRCAT E "0"))
(SETQ B (ATOI B))
(SETQ E (ATOI E))
(SETQ BNAME (ATOI BNAME))


(IF (= BNAME 1515)
    (PROGN
     (setq A 200)
     (setq C 90)
     (setq D 28)
     (setq F 132)
     (setq G 57)
     (setq H 55)
     (setq I 48)
     (setq J 72)
     (setq K 114)
     (setq L 120)
     (setq M 56)
     (setq gp 16)
     (setq rp 12)
     (setq mA 6)
     (setq mB 10)
     (setq n  20 )
     (setq r 13  )
     (setq s 15  )
     (setq t 5  )
   )
)
(IF (= BNAME 1518)
    (PROGN
     (setq A 200)
     (setq C 90)
     (setq D 28)
     (setq F 162)
     (setq G 72)
     (setq H 70)
     (setq I 48)
     (setq J 72)
     (setq K 114)
     (setq L 120)
     (setq M 86)
     (setq gp 16)
     (setq rp 12)
     (setq mA 6)
     (setq mB 10)
     (setq n  20 )
     (setq r 13  )
     (setq s 15  )
     (setq t 5  )
   )
)
(IF (= BNAME 1520)
    (PROGN
     (setq A 200)
     (setq C 90)
     (setq D 28)
     (setq F 182)
     (setq G 82)
     (setq H 80)
     (setq I 48)
     (setq J 72)
     (setq K 114)
     (setq L 120)
     (setq M 106)
     (setq gp 16)
     (setq rp 12)
     (setq mA 6)
     (setq mB 10)
     (setq n  20 )
     (setq r 13  )
     (setq s 15  )
     (setq t 5  )
   )
)
(SETQ RR 1)
(IF (= BNAME 1523)
    (PROGN
     (setq A 200)
     (setq C 90)
     (setq D 28)
     (setq F 212)
     (setq G 97)
     (setq H 95)
     (setq I 48)
     (setq J 72)
     (setq K 114)
     (setq L 120)
     (setq M 136)
     (setq gp 16)
     (setq rp 12)
     (setq mA 6)
     (setq mB 10)
     (setq n  20 )
     (setq r 13  )
     (setq s 15  )
     (setq t 5  )
   )
)
(SETQ RR 2)
(IF (= BNAME 1525)
    (PROGN
     (setq A 200)
     (setq C 90)
     (setq D 28)
     (setq F 232)
     (setq G 107)
     (setq H 105)
     (setq I 48)
     (setq J 72)
     (setq K 114)
     (setq L 120)
     (setq M 156)
     (setq gp 16)
     (setq rp 12)
     (setq mA 6)
     (setq mB 10)
     (setq r  20 )
     (setq s 13  )
     (setq t 15  )
     (setq u 5  )
   )
)
(SETQ RR 3)
(IF (= BNAME 1530)
    (PROGN
     (setq A 200)
     (setq C 90)
     (setq D 28)
     (setq F 282)
     (setq G 132)
     (setq H 130)
     (setq I 48)
     (setq J 72)
     (setq K 114)
     (setq L 120)
     (setq M 206)
     (setq gp 16)
     (setq rp 12)
     (setq mA 6)
     (setq mB 10)
     (setq r  20 )
     (setq s 13  )
     (setq t 15  )
     (setq u 5  )
   )
)
(SETQ RR 4)
(IF (= BNAME 1818)
    (PROGN
     (setq A 230)
     (setq C 110)
     (setq D 33)
     (setq F 160)
     (setq G 67)
     (setq H 65)
     (setq I 68)
     (setq J 90)
     (setq K 134)
     (setq L 145)
     (setq M 64)
     (setq gp 20)
     (setq rp 12)
     (setq mA 8)
     (setq mB 12)
     (setq n  20 )
     (setq r 13  )
     (setq s 15  )
     (setq t 5  )
   )
)
(SETQ RR 5)
(IF (= BNAME 1820)
    (PROGN
     (setq A 230)
     (setq C 110)
     (setq D 33)
     (setq F 180)
     (setq G 77)
     (setq H 75)
     (setq I 68)
     (setq J 90)
     (setq K 134)
     (setq L 145)
     (setq M 84)
     (setq gp 20)
     (setq rp 12)
     (setq mA 8)
     (setq mB 12)
     (setq n  20 )
     (setq r 13  )
     (setq s 15  )
     (setq t 5  )
   )
)
(SETQ RR 6)
(IF (= BNAME 1823)
    (PROGN
     (setq A 230)
     (setq C 110)
     (setq D 33)
     (setq F 210)
     (setq G 92)
     (setq H 90)
     (setq I 68)
     (setq J 90)
     (setq K 134)
     (setq L 145)
     (setq M 114)
     (setq gp 20)
     (setq rp 12)
     (setq mA 8)
     (setq mB 12)
     (setq n  20 )
     (setq r 13  )
     (setq s 15  )
     (setq t 5  )
   )
)
(SETQ RR 7)
(IF (= BNAME 1825)
    (PROGN
     (setq A 230)
     (setq C 110)
     (setq D 33)
     (setq F 230)
     (setq G 102)
     (setq H 100)
     (setq I 68)
     (setq J 90)
     (setq K 134)
     (setq L 145)
     (setq M 124)
     (setq gp 20)
     (setq rp 12)
     (setq mA 8)
     (setq mB 12)
     (setq n  20 )
     (setq r 13  )
     (setq s 15  )
     (setq t 5  )
   )
)
(SETQ RR 8)
(IF (= BNAME 2020)
    (PROGN
     (setq A 250)
     (setq C 120)
     (setq D 38)
     (setq F 180)
     (setq G 77)
     (setq H 75)
     (setq I 84)
     (setq J 100)
     (setq K 154)
     (setq L 160)
     (setq M 80)
     (setq gp 20)
     (setq rp 12)
     (setq mA 8)
     (setq mB 12)
     (setq n  25 )
     (setq r 13  )
     (setq s 15  )
     (setq t 5  )
   )
)
(SETQ RR 9)
(IF (= BNAME 2023)
    (PROGN
     (setq A 250)
     (setq C 120)
     (setq D 38)
     (setq F 210)
     (setq G 92)
     (setq H 90)
     (setq I 80)
     (setq J 100)
     (setq K 154)
     (setq L 160)
     (setq M 110)
     (setq gp 20)
     (setq rp 15)
     (setq mA 8)
     (setq mB 12)
     (setq n  25 )
     (setq r 15  )
     (setq s 20  )
     (setq t 5  )
   )
)
(SETQ RR 10)
(IF (= BNAME 2025)
    (PROGN
     (setq A 250)
     (setq C 120)
     (setq D 38)
     (setq F 230)
     (setq G 102)
     (setq H 100)
     (setq I 80)
     (setq J 100)
     (setq K 154)
     (setq L 160)
     (setq M 130)
     (setq gp 20)
     (setq rp 15)
     (setq mA 8)
     (setq mB 12)
     (setq n  25 )
     (setq r 15  )
     (setq s 20  )
     (setq t 5  )
   )
)
(SETQ RR 11)
(IF (= BNAME 2030)
    (PROGN
     (setq A 250)
     (setq C 120)
     (setq D 38)
     (setq F 280)
     (setq G 127)
     (setq H 125)
     (setq I 80)
     (setq J 100)
     (setq K 154)
     (setq L 160)
     (setq M 180)
     (setq gp 20)
     (setq rp 15)
     (setq mA 8)
     (setq mB 12)
     (setq n  25 )
     (setq r 15  )
     (setq s 20  )
     (setq t 5  )
   )
)
(IF (= BNAME 2035)
    (PROGN
     (setq A 250)
     (setq C 120)
     (setq D 38)
     (setq F 330)
     (setq G 152)
     (setq H 150)
     (setq I 80)
     (setq J 100)
     (setq K 154)
     (setq L 160)
     (setq M 230)
     (setq gp 20)
     (setq rp 15)
     (setq mA 8)
     (setq mB 12)
     (setq n  25 )
     (setq r 15  )
     (setq s 20  )
     (setq t 5  )
   )
)
(IF (= BNAME 2323)
    (PROGN
     (setq A 280)
     (setq C 140)
     (setq D 43)
     (setq F 210)
     (setq G 92)
     (setq H 90)
     (setq I 106)
     (setq J 120)
     (setq K 184)
     (setq L 185)
     (setq M 106)
     (setq gp 20)
     (setq rp 15)
     (setq mA 8)
     (setq mB 12)
     (setq n  25 )
     (setq r 15  )
     (setq s 20  )
     (setq t 5  )
   )
)
(SETQ RR 12)
(IF (= BNAME 2325)
    (PROGN
     (setq A 280)
     (setq C 140)
     (setq D 43)
     (setq F 230)
     (setq G 102)
     (setq H 100)
     (setq I 106)
     (setq J 120)
     (setq K 184)
     (setq L 185)
     (setq M 126)
     (setq gp 20)
     (setq rp 15)
     (setq mA 8)
     (setq mB 12)
     (setq n  25 )
     (setq r 15  )
     (setq s 20  )
     (setq t 5  )
   )
)
(IF (= BNAME 2327)
    (PROGN
     (setq A 280)
     (setq C 140)
     (setq D 43)
     (setq F 250)
     (setq G 112)
     (setq H 110)
     (setq I 106)
     (setq J 120)
     (setq K 184)
     (setq L 185)
     (setq M 144)
     (setq gp 20)
     (setq rp 15)
     (setq mA 8)
     (setq mB 14)
     (setq n  25 )
     (setq r 15  )
     (setq s 20  )
     (setq t 5  )
   )
)
(IF (= BNAME 2330)
    (PROGN
     (setq A 280)
     (setq C 140)
     (setq D 43)
     (setq F 280)
     (setq G 127)
     (setq H 125)
     (setq I 106)
     (setq J 120)
     (setq K 184)
     (setq L 185)
     (setq M 174)
     (setq gp 20)
     (setq rp 15)
     (setq mA 8)
     (setq mB 14)
     (setq n  25 )
     (setq r 15  )
     (setq s 20  )
     (setq t 5  )
   )
)
(SETQ RR 13)
(IF (= BNAME 2525)
    (PROGN
     (setq A 300)
     (setq C 150)
     (setq D 48)
     (setq F 230)
     (setq G 97)
     (setq H 95)
     (setq I 110)
     (setq J 130)
     (setq K 194)
     (setq L 200)
     (setq M 108)
     (setq gp 25)
     (setq rp 15)
     (setq mA 8)
     (setq mB 14)
     (setq n  25 )
     (setq r 15  )
     (setq s 20  )
     (setq t 5  )
   )
)
(IF (= BNAME 2527)
    (PROGN
     (setq A 300)
     (setq C 150)
     (setq D 48)
     (setq F 250)
     (setq G 107)
     (setq H 105)
     (setq I 110)
     (setq J 130)
     (setq K 194)
     (setq L 200)
     (setq M 128)
     (setq gp 25)
     (setq rp 15)
     (setq mA 8)
     (setq mB 14)
     (setq n  25 )
     (setq r 15  )
     (setq s 20  )
     (setq t 5  )
   )
)
(SETQ RR 14)
(IF (= BNAME 2530)
    (PROGN
     (setq A 300)
     (setq C 150)
     (setq D 48)
     (setq F 280)
     (setq G 122)
     (setq H 120)
     (setq I 110)
     (setq J 130)
     (setq K 194)
     (setq L 200)
     (setq M 154)
     (setq gp 25)
     (setq rp 15)
     (setq mA 8)
     (setq mB 14)
     (setq n  25 )
     (setq r 15  )
     (setq s 20  )
     (setq t 5  )
   )
)
(IF (= BNAME 2535)
    (PROGN
     (setq A 300)
     (setq C 150)
     (setq D 48)
     (setq F 330)
     (setq G 147)
     (setq H 145)
     (setq I 102)
     (setq J 130)
     (setq K 194)
     (setq L 200)
     (setq M 204)
     (setq gp 25)
     (setq rp 20)
     (setq mA 8)
     (setq mB 14)
     (setq n  25 )
     (setq r 15  )
     (setq s 20  )
     (setq t 5  )
   )
)
(IF (= BNAME 2540)
    (PROGN
     (setq A 300)
     (setq C 150)
     (setq D 48)
     (setq F 380)
     (setq G 172)
     (setq H 170)
     (setq I 102)
     (setq J 130)
     (setq K 194)
     (setq L 200)
     (setq M 254)
     (setq gp 25)
     (setq rp 20)
     (setq mA 8)
     (setq mB 14)
     (setq n  25 )
     (setq r 15  )
     (setq s 20  )
     (setq t 5  )
   )
)
(SETQ RR 15)
(IF (= BNAME 2730)
    (PROGN
     (setq A 320)
     (setq C 160)
     (setq D 53)
     (setq F 276)
     (setq G 122)
     (setq H 120)
     (setq I 114)
     (setq J 136)
     (setq K 214)
     (setq L 215)
     (setq M 154)
     (setq gp 25)
     (setq rp 20)
     (setq mA 10)
     (setq mB 14)
     (setq n  25 )
     (setq r 15  )
     (setq s 20  )
     (setq t 5  )
   )
)
(IF (= BNAME 2735)
    (PROGN
     (setq A 320)
     (setq C 160)
     (setq D 53)
     (setq F 326)
     (setq G 147)
     (setq H 145)
     (setq I 114)
     (setq J 136)
     (setq K 214)
     (setq L 215)
     (setq M 204)
     (setq gp 25)
     (setq rp 20)
     (setq mA 10)
     (setq mB 14)
     (setq n  25 )
     (setq r 15  )
     (setq s 20  )
     (setq t 5  )
   )
)
(IF (= BNAME 3030)
    (PROGN
     (setq A 350)
     (setq C 180)
     (setq D 58)
     (setq F 276)
     (setq G 117)
     (setq H 115)
     (setq I 134)
     (setq J 156)
     (setq K 234)
     (setq L 240)
     (setq M 138)
     (setq gp 30)
     (setq rp 20)
     (setq mA 10)
     (setq mB 14)
     (setq n  25 )
     (setq r 20  )
     (setq s 25  )
     (setq t 5  )
   )
)
(IF (= BNAME 3035)
    (PROGN
     (setq A 350)
     (setq C 180)
     (setq D 58)
     (setq F 326)
     (setq G 142)
     (setq H 140)
     (setq I 134)
     (setq J 156)
     (setq K 234)
     (setq L 240)
     (setq M 188)
     (setq gp 30)
     (setq rp 20)
     (setq mA 10)
     (setq mB 14)
     (setq n  25 )
     (setq r 20  )
     (setq s 25  )
     (setq t 5  )
   )
)
(SETQ RR 16)
 (IF (= BNAME 3040)
  (PROGN
      (setq A 350)
      (setq C 180)
      (setq D 58)
      (setq F 376)
      (setq G 167)
      (setq H 165)
      (setq I 134)
      (setq J 156)
      (setq K 234)
      (setq L 240)
      (setq M 238)
      (setq gp 30)
      (setq rp 20)
      (setq mA 10)
      (setq mB 14)
      (setq n  30)
      (setq r 20 )
      (setq s 25 )
      (setq t 5 )
    )
 )
(IF (= BNAME 3045)
    (PROGN
     (setq A 350)
     (setq C 180)
     (setq D 58)
     (setq F 426)
     (setq G 192)
     (setq H 190)
     (setq I 128)
     (setq J 156)
     (setq K 234)
     (setq L 240)
     (setq M 288)
     (setq gp 30)
     (setq rp 25)
     (setq mA 10)
     (setq mB 16)
     (setq n  30 )
     (setq r 20  )
     (setq s 25  )
     (setq t 5  )
   )
)
(IF (= BNAME 3050)
    (PROGN
     (setq A 350)
     (setq C 180)
     (setq D 58)
     (setq F 476)
     (setq G 217)
     (setq H 215)
     (setq I 128)
     (setq J 156)
     (setq K 234)
     (setq L 240)
     (setq M 338)
     (setq gp 30)
     (setq rp 25)
     (setq mA 10)
     (setq mB 16)
     (setq n  30)
     (setq r 20 )
     (setq s 25 )
     (setq t 5 )
   )
)
(IF (= BNAME 3060)
    (PROGN
     (setq A 350)
     (setq C 180)
     (setq D 58)
     (setq F 576)
     (setq G 267)
     (setq H 265)
     (setq I 128)
     (setq J 156)
     (setq K 234)
     (setq L 240)
     (setq M 438)
     (setq gp 30)
     (setq rp 20)
     (setq mA 10)
     (setq mB 16)
     (setq n  30)
     (setq r 20 )
     (setq s 25 )
     (setq t 5  )
   )
)
(SETQ RR 17)
(IF (= BNAME 3335)
    (PROGN
     (setq A 380)
     (setq C 210)
     (setq D 58)
     (setq F 326)
     (setq G 142)
     (setq H 140)
     (setq I 154)
     (setq J 186)
     (setq K 264)
     (setq L 270)
     (setq M 188)
     (setq gp 30)
     (setq rp 25)
     (setq mA 10)
     (setq mB 14)
     (setq n  30)
     (setq r 20 )
     (setq s 25 )
     (setq t 5 )
   )
)
(IF (= BNAME 3340)
    (PROGN
     (setq A 380)
     (setq C 210)
     (setq D 58)
     (setq F 376)
     (setq G 167)
     (setq H 165)
     (setq I 154)
     (setq J 186)
     (setq K 264)
     (setq L 270)
     (setq M 238)
     (setq gp 30)
     (setq rp 25)
     (setq mA 10)
     (setq mB 14)
     (setq n  30 )
     (setq r 20  )
     (setq s 25  )
     (setq t 5  )
   )
)
(SETQ RR 18)
(IF (= BNAME 3535)
    (PROGN
     (setq A 400)
     (setq C 220)
     (setq D 63)
     (setq F 326)
     (setq G 142)
     (setq H 140)
     (setq I 164)
     (setq J 196)
     (setq K 284)
     (setq L 285)
     (setq M 178)
     (setq gp 30)
     (setq rp 25)
     (setq mA 10)
     (setq mB 16)
     (setq n  30 )
     (setq r 20  )
     (setq s 25  )
     (setq t 5  )
   )
)
(IF (= BNAME 3540)
    (PROGN
     (setq A 400)
     (setq C 220)
     (setq D 63)
     (setq F 376)
     (setq G 167)
     (setq H 165)
     (setq I 164)
     (setq J 196)
     (setq K 284)
     (setq L 285)
     (setq M 224)
     (setq gp 30)
     (setq rp 25)
     (setq mA 10)
     (setq mB 16)
     (setq n  30 )
     (setq r 20  )
     (setq s 25  )
     (setq t 5  )
   )
)
(IF (= BNAME 3545)
    (PROGN
     (setq A 400)
     (setq C 220)
     (setq D 63)
     (setq F 426)
     (setq G 192)
     (setq H 190)
     (setq I 164)
     (setq J 196)
     (setq K 284)
     (setq L 285)
     (setq M 274)
     (setq gp 30)
     (setq rp 25)
     (setq mA 10)
     (setq mB 16)
     (setq n  30 )
     (setq r 20  )
     (setq s 25  )
     (setq t 5  )
   )
)
(IF (= BNAME 3550)
    (PROGN
     (setq A 400)
     (setq C 220)
     (setq D 63)
     (setq F 476)
     (setq G 212)
     (setq H 210)
     (setq I 152)
     (setq J 196)
     (setq K 274)
     (setq L 285)
     (setq M 308)
     (setq gp 35)
     (setq rp 25)
     (setq mA 10)
     (setq mB 16)
     (setq n  30 )
     (setq r 20  )
     (setq s 25  )
     (setq t 5  )
   )
)
(IF (= BNAME 3560)
    (PROGN
     (setq A 400)
     (setq C 220)
     (setq D 63)
     (setq F 576)
     (setq G 262)
     (setq H 260)
     (setq I 152)
     (setq J 196)
     (setq K 274)
     (setq L 285)
     (setq M 408)
     (setq gp 35)
     (setq rp 25)
     (setq mA 10)
     (setq mB 16)
     (setq n  30 )
     (setq r 20  )
     (setq s 25  )
     (setq t 5  )
   )
)
(IF (= BNAME 4040)
    (PROGN
     (setq A 450)
     (setq C 260)
     (setq D 68)
     (setq F 374)
     (setq G 162)
     (setq H 160)
     (setq I 198)
     (setq J 234)
     (setq K 324)
     (setq L 330)
     (setq M 208)
     (setq gp 35)
     (setq rp 25)
     (setq mA 12)
     (setq mB 16)
     (setq n  30 )
     (setq r 25  )
     (setq s 30  )
     (setq t 5  )
   )
)
(IF (= BNAME 4045)
    (PROGN
     (setq A 450)
     (setq C 260)
     (setq D 68)
     (setq F 424)
     (setq G 187)
     (setq H 185)
     (setq I 198)
     (setq J 234)
     (setq K 324)
     (setq L 330)
     (setq M 254)
     (setq gp 35)
     (setq rp 25)
     (setq mA 12)
     (setq mB 16)
     (setq n  35 )
     (setq r 25  )
     (setq s 30  )
     (setq t 5  )
   )
)
(IF (= BNAME 4050)
    (PROGN
     (setq A 450)
     (setq C 260)
     (setq D 68)
     (setq F 474)
     (setq G 212)
     (setq H 210)
     (setq I 198)
     (setq J 234)
     (setq K 324)
     (setq L 330)
     (setq M 304)
     (setq gp 35)
     (setq rp 25)
     (setq mA 12)
     (setq mB 16)
     (setq n  35 )
     (setq r 25  )
     (setq s 30  )
     (setq t 5  )
   )
)
(IF (= BNAME 4060)
    (PROGN
     (setq A 450)
     (setq C 260)
     (setq D 68)
     (setq F 574)
     (setq G 262)
     (setq H 260)
     (setq I 198)
     (setq J 234)
     (setq K 324)
     (setq L 330)
     (setq M 404)
     (setq gp 35)
     (setq rp 25)
     (setq mA 12)
     (setq mB 16)
     (setq n  35 )
     (setq r 25  )
     (setq s 30  )
     (setq t 5  )
   )
)
(IF (= BNAME 4070)
    (PROGN
     (setq A 450)
     (setq C 260)
     (setq D 68)
     (setq F 674)
     (setq G 312)
     (setq H 310)
     (setq I 198)
     (setq J 234)
     (setq K 324)
     (setq L 330)
     (setq M 504)
     (setq gp 35)
     (setq rp 25)
     (setq mA 12)
     (setq mB 16)
     (setq n  35 )
     (setq r 25  )
     (setq s 30  )
     (setq t 5  )
   )
)
(IF (= BNAME 4545)
    (PROGN
     (setq A 500)
     (setq C 290)
     (setq D 78)
     (setq F 424)
     (setq G 182)
     (setq H 180)
     (setq I 226)
     (setq J 264)
     (setq K 364)
     (setq L 370)
     (setq M 236)
     (setq gp 40)
     (setq rp 30)
     (setq mA 12)
     (setq mB 16)
     (setq n  35 )
     (setq r 25  )
     (setq s 30  )
     (setq t 5  )
   )
)
(IF (= BNAME 4550)
    (PROGN
     (setq A 500)
     (setq C 290)
     (setq D 78)
     (setq F 474)
     (setq G 207)
     (setq H 205)
     (setq I 226)
     (setq J 264)
     (setq K 364)
     (setq L 370)
     (setq M 286)
     (setq gp 40)
     (setq rp 30)
     (setq mA 12)
     (setq mB 16)
     (setq n  35 )
     (setq r 25  )
     (setq s 30  )
     (setq t 5  )
   )
)
(IF (= BNAME 5050)
    (PROGN
     (setq A 550)
     (setq C 320)
     (setq D 88)
     (setq F 474)
     (setq G 207)
     (setq H 205)
     (setq I 256)
     (setq J 294)
     (setq K 410)
     (setq L 414)
     (setq M 286)
     (setq gp 40)
     (setq rp 30)
     (setq mA 12)
     (setq mB 16)
     (setq n  35 )
     (setq r 25  )
     (setq s 30  )
     (setq t 5  )
   )
)
(IF (= BNAME 5060)
    (PROGN
     (setq A 550)
     (setq C 320)
     (setq D 88)
     (setq F 574)
     (setq G 257)
     (setq H 255)
     (setq I 256)
     (setq J 294)
     (setq K 410)
     (setq L 414)
     (setq M 386)
     (setq gp 40)
     (setq rp 30)
     (setq mA 12)
     (setq mB 16)
     (setq n  35 )
     (setq r 25  )
     (setq s 30  )
     (setq t 5  )
   )
)
(IF (= BNAME 5070)
    (PROGN
     (setq A 550)
     (setq C 320)
     (setq D 88)
     (setq F 674)
     (setq G 307)
     (setq H 305)
     (setq I 256)
     (setq J 294)
     (setq K 410)
     (setq L 414)
     (setq M 486)
     (setq gp 40)
     (setq rp 30)
     (setq mA 12)
     (setq mB 16)
     (setq n  35 )
     (setq r 25  )
     (setq s 30  )
     (setq t 5  )
   )
)


(SETQ P2 (LIST (+ (CAR P1) A)(CADR P1)))
(SETQ P3 (LIST (CAR P2 ) (- (CADR P2) E)))
(SETQ P4 (LIST (- (CAR P3) A) (CADR P3)))
(SETQ P5 (LIST (/ (+ (CAR P1) (CAR P2)) 2) (+ (CADR P1) 10))) ;CENTER LINE UP
(SETQ P6 (LIST (/ (+ (CAR P3) (CAR P4)) 2) (- (CADR P4) 10)));CENTER LINE DOWN
(SETQ P7 (LIST (- (/ (+ (CAR P1) (CAR P4)) 2) 10) (/ (+ (CADR P1) (CADR P4)) 2)));CENTER LINE LEGT
(SETQ P8 (LIST (+ (/ (+ (CAR P2) (CAR P3)) 2) 10) (/ (+ (CADR P2) (CADR P3)) 2)));RIGHT
(COMMAND "LAYER" "S" "draw" "")
(COMMAND "LINE" P1 P2 P3 P4 "C")
(COMMAND "LAYER" "S"  "CENTER" "")
(COMMAND "LINE" P5 P6 "" "LINE" P7 P8 "") ;DRAW CENETR
(COMMAND "LAYER" "S"  "HIDDEN" "")
(COMMAND "LINE" (LIST (+ (CAR P5) (/ C 2))  (- (CADR P5) 10))
                (LIST (+ (CAR P6) (/ C 2))  (+ (CADR P6) 10)) "")
(COMMAND "LINE" (LIST (- (CAR P5) (/ C 2))  (- (CADR P5) 10))
                (LIST (- (CAR P6) (/ C 2))  (+ (CADR P6) 10)) "")
(COMMAND "LINE" (LIST (+ (CAR P5) (/ C 2) 2)  (- (CADR P5) 10))
                (LIST (+ (CAR P6) (/ C 2) 2)  (+ (CADR P6) 10)) "")
(COMMAND "LINE" (LIST (- (CAR P5) (/ C 2) 2)  (- (CADR P5) 10))
                (LIST (- (CAR P6) (/ C 2) 2)  (+ (CADR P6) 10)) "")
(SETQ SD (/ (- B C (* D 2)) 2))

(COMMAND "LINE" (LIST (+ (CAR P5) (/ C 2))  (- (CADR P5) 10))
                (LIST (+ (CAR P6) (/ C 2))  (+ (CADR P6) 10)) "")
(COMMAND "LINE" (LIST (- (CAR P5) (/ C 2))  (- (CADR P5) 10))
                (LIST (- (CAR P6) (/ C 2))  (+ (CADR P6) 10)) "")

(COMMAND "LAYER" "S"  "DRAW" "")
(COMMAND "LINE" (LIST (+ (CAR P5) (/ B 2))  (- (CADR P5) 10))
                (LIST (+ (CAR P6) (/ B 2))  (+ (CADR P6) 10)) "")
(COMMAND "LINE" (LIST (- (CAR P5) (/ B 2))  (- (CADR P5) 10))
                (LIST (- (CAR P6) (/ B 2))  (+ (CADR P6) 10)) "")
(SETQ D1 (/ (- A B) 2))
(SETQ D2 (+ (/ (- A B) 2 ) D))
(SETQ D3 (+ (/ (- A B) 2 ) D (/ (- B C  D D ) 2)))

(SETQ C4 (LIST (+ (CAR P6) (/ K 2)) (-(CADR P8) H))) ;G.P
(SETQ C3 (LIST (- (CAR P6) (/ K 2)) (-(CADR P8) G)))
(SETQ C2 (LIST (+ (CAR P5) (/ K 2)) (+(CADR P8) G)))
(SETQ C1 (LIST (- (CAR P5) (/ K 2)) (+(CADR P8) G)))
(SETQ M4 (LIST (+ (CAR P6) (/ j 2)) (- (CADR P8) (/ f 2) )))
(SETQ M3 (LIST (- (CAR P6) (/ j 2)) (- (CADR P8) (/ f 2) )))
(SETQ M2 (LIST (+ (CAR P5) (/ J 2)) (+ (CADR P8) (/ f 2) )))
(SETQ M1 (LIST (- (CAR P5) (/ J 2)) (+ (CADR P8) (/ f 2) )))
(SETQ Y4 (LIST (+ (CAR P6) (/ L 2)) (- (CADR P8) (/ m 2) )))
(SETQ Y3 (LIST (- (CAR P6) (/ L 2)) (- (CADR P8) (/ m 2) )))
(SETQ Y2 (LIST (+ (CAR P5) (/ L 2)) (+ (CADR P8) (/ m 2) )))
(SETQ Y1 (LIST (- (CAR P5) (/ L 2)) (+ (CADR P8) (/ m 2) )))
(SETQ R4 (LIST (+ (CAR P6) (/ i 2)) (- (CADR P8) G)))
(SETQ R3 (LIST (- (CAR P6) (/ i 2)) (- (CADR P8) G)))
(SETQ R2 (LIST (+ (CAR P5) (/ i 2)) (+ (CADR P8) G)))
(SETQ R1 (LIST (- (CAR P5) (/ i 2)) (+ (CADR P8) G)))
(SETQ Y5 (LIST (- (CAR P6) (/ L 2)) (- (CADR P8) 0)))
(SETQ Y6 (LIST (+ (CAR P5) (/ L 2)) (+ (CADR P8) 0)))

(SETQ GP (ITOA GP))
(SETQ GP-1 (STRCAT "C:\\acad\\HON\\G\\GP" GP ))
(SETQ GP11 (STRCAT "C:\\acad\\HON\\G\\GP" GP "-1"))
(command "insert" GP11 C4 1 1 0)
(command "insert" GP-1 C3 1 1 0)
(command "insert" GP-1 C2 1 1 0)
(command "insert" GP-1 C1 1 1 0)
(SETQ RP (ITOA RP))
(SETQ RP-1 (STRCAT "C:\\acad\\HON\\R\\RP" RP "-1"))
(command "insert" RP-1 R4 1 1 0)
(command "insert" RP-1 R3 1 1 0)
(command "insert" RP-1 R2 1 1 0)
(command "insert" RP-1 R1 1 1 0)

(SETQ MA (ITOA MA))
(SETQ MA-1 (STRCAT "C:\\acad\\HON\\B\\BLT1-" MA))
(command "insert" MA-1 M4 1 1 0)
(command "insert" MA-1 M3 1 1 0)
(command "insert" MA-1 M2 1 1 0)
(command "insert" MA-1 M1 1 1 0)

(SETQ MB (ITOA MB))
(SETQ MB-1 (STRCAT "C:\\acad\\HON\\B\\BLT1-" MB))
(command "insert" MB-1 Y4 1 1 0)
(command "insert" MB-1 Y3 1 1 0)
(command "insert" MB-1 Y2 1 1 0)
(command "insert" MB-1 Y1 1 1 0)
(IF (> BNAME 2530)
     (PROGN
      (command "insert" MB-1 Y5 1 1 0)
      (command "insert" MB-1 Y6 1 1 0)
     )
)
(SETQ GP (ATOI GP))
(SETQ RP (ATOI RP))
(SETQ MA (ATOI MA))
(SETQ MB (ATOI MB))

(COMMAND "LAYER" "S" "DRAW" "")

(SETQ T1 A1)
; 2ST PICTURE
;DRAW BOX
(SETQ P1 (LIST (CAR P1) (- (CADR P1) E 100)))  ;SECOND ORG P1
(SETQ Z1 P1)
(SETQ W2 P1)
(COMMAND "LINE" P1 (LIST (+ A (CAR P1)) (CADR P1)) (LIST (+ A (CAR P1)) ;1ST BOX
(- (CADR P1) N)) (LIST (CAR P1 ) (- (CADR P1) N )) P1 "")
;
(SETQ P1 (LIST (+ (CAR P1) (/ (- A B ) 2) ) (- (CADR P1 ) N))) ;2ND BO3
(COMMAND "LINE" (LIST (+ B (CAR P1)) (CADR P1))
(LIST (+ B (CAR P1)) (- (CADR P1 ) O))
(LIST (CAR P1) (- (CADR P1) O)) P1 "")
;
(SETQ P1 (LIST (CAR P1) (- (CADR P1 ) O) ))                   ;3ND BO3
(COMMAND "LINE" (LIST (+ B (CAR P1)) (CADR P1))
(LIST (+ B (CAR P1)) (- (CADR P1 ) P))
(LIST (CAR P1) (- (CADR P1) P)) P1 "")
;
(SETQ P1 (LIST (CAR P1) (- (CADR P1 ) P) ))                   ;4ND BOX
(COMMAND "LINE" (LIST (+ B (CAR P1)) (CADR P1))
(LIST (+ B (CAR P1)) (- (CADR P1 ) Q)) "")
(COMMAND "LINE" (LIST (CAR P1) (- (CADR P1) Q)) P1 "")


;LAST BOX
 (SETQ T1 (+ N O P Q ))
 (SETQ Q1 (LIST  (CAR Z1) (- (CADR Z1 ) T1)))
 (COMMAND "LINE" Q1 (LIST (+ (CAR Q1) A) (CADR Q1))
                   (LIST (+ (CAR Q1) A) (- (CADR Q1) N))
                   (LIST (CAR Q1)       (- (CADR Q1) N)) Q1 "")


;6ND BO3  INSIDE 1
(SETQ P1 (LIST (+ (CAR Z1) (+ D (/ (- A B) 2)) (/ (- B C D D ) 2))
               (+ (- (CADR Z1) N O P Q ) R S T)))
(COMMAND "LINE" P1 (LIST (+ C (CAR P1)) (CADR P1))
(LIST (+ C (CAR P1)) (- (CADR P1 ) R)) "")
(COMMAND "LINE"  (LIST (CAR P1) (- (CADR P1) R)) P1 "")

;INSIDE 2
 (SETQ P1 (LIST (+ (CAR Z1) (+ D (/ (- A B) 2)) (/ (- B C D D ) 2))
                (+ (- (CADR Z1 ) N O P Q ) S T)))
(COMMAND "LINE" P1 (LIST (+ C (CAR P1)) (CADR P1))
 (LIST (+ C (CAR P1)) (- (CADR P1 ) S)) "")
(COMMAND "LINE" (LIST (CAR P1) (- (CADR P1) S)) P1 "")
(command "line" (list (+ c (car p1)) (- (cadr p1 ) s))
 (list (car p1) (- (cadr p1 )s)) "")


(COMMAND "LAYER" "S" "CENTER" "")
(COMMAND "LINE" (LIST (+ (CAR Z1) (/ A 2)) (+ (CADR Z1) 10))
                (LIST (+ (CAR Z1) (/ A 2)) (- (CADR Z1) 10 N O P Q N)) "")

(COMMAND "LAYER" "S" "DRAW" "")
(SETQ P1 (LIST (+ (CAR Z1) (/ (- A E ) 2)) (- (CADR Z1) N O P )))

; TWO LINE
(SETQ I1 (LIST (CAR Z1) (- (CADR Z1) N O P )))
(SETQ I3 (LIST (-  (+ (CAR I1) A)  D (/ ( - A B) 2)) (CADR I1) ) )
(COMMAND "LINE" I3 (LIST (CAR I3) (- (CADR I3) Q)  ) "")

(SETQ I4 (LIST (+ (CAR I1) D (/ ( - A B) 2)) (CADR I1) ) )
(COMMAND "LINE" I4 (LIST (CAR I4) (- (CADR I4) Q)  ) "")

;THIRD PICTURE
(SETQ P1 (LIST (+ (CAR W1) 100 A) (CADR W1)))
(SETQ P2 (LIST (+ (CAR P1) A)(CADR P1)))
(SETQ P3 (LIST (CAR P2 ) (- (CADR P2) E)))
(SETQ P4 (LIST (- (CAR P3) A) (CADR P3)))
(SETQ P5 (LIST (/ (+ (CAR P1) (CAR P2)) 2) (+ (CADR P1) 10))) ;CENTER LINE UP
(SETQ P6 (LIST (/ (+ (CAR P3) (CAR P4)) 2) (- (CADR P4) 10)));CENTER LINE DOWN
(SETQ P7 (LIST (- (/ (+ (CAR P1) (CAR P4)) 2) 10) (/ (+ (CADR P1) (CADR P4)) 2)));CENTER LINE LEGT
(SETQ P8 (LIST (+ (/ (+ (CAR P2) (CAR P3)) 2) 10) (/ (+ (CADR P2) (CADR P3)) 2)));RIGHT
(COMMAND "LAYER" "S" "DRAW" "")
(COMMAND "LINE" P1 P2 P3 P4 "C")
(COMMAND "LAYER" "S"  "CENTER" "")
(COMMAND "LINE" P5 P6 "" "LINE" P7 P8 "") ;DRAW CENETR
(SETQ D1 (/ (- A B) 2))
(SETQ D2 (+ (/ (- A B) 2 ) D))
(SETQ D3 (+ (/ (- A B) 2 ) D (/ (- B C  D D ) 2)))
(COMMAND "LAYER" "S" "DRAW" "")
(COMMAND "LINE" (LIST (+ (CAR P5) (/ B 2)) (- (CADR P5) 10)) ;DRAW CENETR RIGTH
                (LIST (+ (CAR P6) (/ B 2)) (+ (CADR P6) 10)) "")
(COMMAND "LINE" (LIST (- (CAR P5) (/ B 2)) (- (CADR P5) 10)) ;DRAW CENETR RIGTH
                (LIST (- (CAR P6) (/ B 2)) (+ (CADR P6) 10)) "")


(COMMAND "LAYER" "S" "CENTER" "")
(SETQ T4 (LIST (+ (CAR C4 ) A 100) (CADR C3 )))
(SETQ T3 (LIST (+ (CAR C3 ) A 100) (CADR C4 )))
(SETQ T2 (LIST (+ (CAR C2 ) A 100) (CADR C1 )))
(SETQ T1 (LIST (+ (CAR C1 ) A 100) (CADR C2 )))
(SETQ Y4 (LIST (+ (CAR Y4 ) A 100) (CADR Y4 )))
(SETQ Y3 (LIST (+ (CAR Y3 ) A 100) (CADR Y3 )))
(SETQ Y2 (LIST (+ (CAR Y2 ) A 100) (CADR Y2 )))
(SETQ Y1 (LIST (+ (CAR Y1 ) A 100) (CADR Y1 )))
(SETQ Y5 (LIST (+ (CAR Y5 ) A 100) (CADR Y5 )))
(SETQ Y6 (LIST (+ (CAR Y6 ) A 100) (CADR Y6 )))


(SETQ GP (ITOA GP))
(SETQ GP-2 (STRCAT "C:\\acad\\HON\\G\\GB" GP ))
(SETQ GP22 (STRCAT "C:\\acad\\HON\\G\\GB" GP "-1"))
(command "insert" GP22 T3 1 1 0)              
(command "insert" GP-2 T4 1 1 0)
(command "insert" GP-2 T1 1 1 0)
(command "insert" GP-2 T2 1 1 0)

(SETQ MB (ITOA MB))
(SETQ MB-2 (STRCAT "C:\\acad\\HON\\B\\BLT1-" MB))
(command "insert" MB-2 Y4 1 1 0)
(command "insert" MB-2 Y3 1 1 0)
(command "insert" MB-2 Y2 1 1 0)
(command "insert" MB-2 Y1 1 1 0)
(IF (> BNAME 2530)
     (PROGN
      (command "insert" MB-2 Y5 1 1 0)
      (command "insert" MB-2 Y6 1 1 0)
     )
)


;FOURTH PICTURE
(COMMAND "LINE" (LIST (+ 100 A (/ E 2) (CAR Z1)) (+ (CADR Z1) 10))
                (LIST (+ 100 A (/ E 2) (CAR Z1)) (- (CADR Z1) 10 N O P Q  N)) "" )
;CENTER LINE
;
(COMMAND "LAYER" "S" "DRAW" "")
(COMMAND "LINE"
(LIST (+ 100 A (CAR Z1)) (CADR Z1))
(LIST (+ 100 A E (CAR Z1)) (CADR Z1))
(LIST (+ 100 A E (CAR Z1 ) ) (- (CADR Z1) N O P Q  N ))
(LIST (+ 100 A (CAR Z1 ) ) (- (CADR Z1) N O P Q N )) "C")


;HERE
(SETQ Z1 (LIST (+ 100 A (CAR Z1)) (CADR Z1)))
(COMMAND "LINE" (LIST (CAR Z1)       (- (CADR Z1) N))
                (LIST (+ (CAR Z1) E) (- (CADR Z1) N)) "")
(COMMAND "LINE" (LIST (CAR Z1)       (- (CADR Z1) (+ N O )))
                (LIST (+ (CAR Z1) E) (- (CADR Z1) (+ N O ))) "")
(COMMAND "LINE" (LIST (CAR Z1)       (- (CADR Z1) (+ N O P)))
                (LIST (+ (CAR Z1) E) (- (CADR Z1) (+ N O P))) "")


(COMMAND "LINE" (LIST (CAR Z1)       (- (CADR Z1) (+ N O P Q)))
                (LIST (+ (CAR Z1) E) (- (CADR Z1) (+ N O P Q))) "")

(COMMAND "MENU" "ACAD4")

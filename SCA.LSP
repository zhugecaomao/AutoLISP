DEFUN C:SCA
(SETQ SC (GETREAL"\nSCALE REFERENCE:"))
(COMMAND "SETVAR" "HIGHLIGHT" "1")
(COMMAND "SELECT" "AU" "\\")
(SETQ SA (SSGET "P" ))
(SETQ P1 (GETPOINT"\nBASE POINT:"))
(SETQ N (SSLENGTH SA))
(COMMAND "SCALE" "P" "" P1 SC)
(COMMAND "SELECT" "C" (GETVAR "EXTMIN") (GETVAR "EXTMAX") "")
(SETQ SA1 (SSGET "P" ))
(SETQ N1 (SSLENGTH SA1))
(SETQ I1 0)
(REPEAT N1
  (SETQ NA1 (ENTGET (SSNAME SA1 I1)))
  (SETQ I1 (+ 1 I1))
  (SETQ NB1 (ASSOC 0 NA1))
  (IF (= "TEXT" (CDR NB1))
      (PROGN
          (SETQ IP1 (ASSOC 10 NA1))
          (SETQ IP1 (CDR IP1))
          (SETQ TH1 (ASSOC 40 NA1))
          (SETQ TH1 (CDR TH1))
          (SETQ TH1 (/ TH1 SC))
          (SETQ NA1 (SUBST (CONS 40 TH1) (ASSOC 40 NA1) NA1))
          (ENTMOD NA1)
       )
  )
)

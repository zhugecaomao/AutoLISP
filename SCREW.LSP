(DEFUN C:SCREW ()
   (SETVAR "CMDECHO" 0)
   (SETQ VC (GETVAR "VIEWCTR"))
   (SETQ YR (GETVAR "VIEWSIZE"))
   (SETQ CY (GETVAR "CLAYER"))
 ;  (COMMAND "LAYER")
   (COMMAND "LAYER" "S" "SCREW" "")
   (SETQ XR (* YR 1.3864))
   (SETQ YD (/ YR 8))
   (SETQ XD (/ XR 14))
   (SETQ XB (- (CAR VC) (/ XR 2)))
   (SETQ YB (- (CADR VC) (/ YR 2)))
   (COMMAND "VSLIDE" "C:/ACAD/SLIDE/SCREW")
;----
        (SETQ PT (GETPOINT "\nPLEASE DIGIT THE CHAR. TABLE : "))
             (SETQ XP (CAR PT))
             (SETQ YP (CADR PT))
             (SETQ XAA (- XP XB))
             (SETQ YAA (- YP YB))
             (SETQ XA (ABS XAA))
             (SETQ YA (ABS YAA))
             (SETQ X (FIX ( / XA XD)))
             (SETQ Y (FIX ( / YA YD)))
        (SETQ OO "D=")
        (SETQ PP "E")
        (SETQ QQ "A")
        (SETQ RR "C=")
        (SETQ SS "F")
        (SETQ TT "B")
        (SETQ AA "C:\\ACAD\\BLOCK\\M03-")
        (SETQ BB "C:\\ACAD\\BLOCK\\M04-")
        (SETQ CC "C:\\ACAD\\BLOCK\\M05-")
        (SETQ DD "C:\\ACAD\\BLOCK\\M06-")
        (SETQ EE "C:\\ACAD\\BLOCK\\M08-")
        (SETQ FF "C:\\ACAD\\BLOCK\\M10-")                         
        (SETQ GG "C:\\ACAD\\BLOCK\\M12-")
        (SETQ HH "C:\\ACAD\\BLOCK\\M14-")
        (SETQ II "C:\\ACAD\\BLOCK\\M16-")
        (SETQ JJ "C:\\ACAD\\BLOCK\\M20-")
        (SETQ KK "C:\\ACAD\\BLOCK\\M24-")
        (SETQ LL "C:\\ACAD\\BLOCK\\M30-")
        (SETQ MM "C:\\ACAD\\BLOCK\\M36-")
    ;   (LOAD "C:/ACAD/ATON/CHANGE")
 ;            (COMMAND "LAYER" "S" CY)           
      (IF (AND (<= X 3) (= Y 0))
      (PROGN
   ;    (SETQ ABC 1))
   ;    (WHILE (<= ABC 1)
        (SETQ A (STRCAT "M03-" OO AA PP))
        (SETQ B (STRCAT "M04-" OO BB PP))
        (SETQ C (STRCAT "M05-" OO CC PP))
        (SETQ D (STRCAT "M06-" OO DD PP))
        (SETQ E (STRCAT "M08-" OO EE PP))
        (SETQ F (STRCAT "M10-" OO FF PP))
        (SETQ G (STRCAT "M12-" OO GG PP))
        (SETQ H (STRCAT "M14-" OO HH PP))
        (SETQ I (STRCAT "M16-" OO II PP))
        (SETQ J (STRCAT "M20-" OO JJ PP))
        (SETQ K (STRCAT "M24-" OO KK PP))
        (SETQ L (STRCAT "M30-" OO LL PP))
        (SETQ M (STRCAT "M36-" OO MM PP))
      (COMMAND "REDRAW" "INSERT" A "1200,800" 1 1 0 "")
      (COMMAND "REDRAW" "INSERT" B "1200,800" 1 1 0 "")
      (COMMAND "REDRAW" "INSERT" C "1200,800" 1 1 0 "")
      (COMMAND "REDRAW" "INSERT" D "1200,800" 1 1 0 "")
      (COMMAND "REDRAW" "INSERT" E "1200,800" 1 1 0 "")
      (COMMAND "REDRAW" "INSERT" F "1200,800" 1 1 0 "")
      (COMMAND "REDRAW" "INSERT" G "1200,800" 1 1 0 "")
      (COMMAND "REDRAW" "INSERT" H "1200,800" 1 1 0 "")
      (COMMAND "REDRAW" "INSERT" I "1200,800" 1 1 0 "")
      (COMMAND "REDRAW" "INSERT" J "1200,800" 1 1 0 "")
      (COMMAND "REDRAW" "INSERT" K "1200,800" 1 1 0 "")
      (COMMAND "REDRAW" "INSERT" L "1200,800" 1 1 0 "")
      (COMMAND "REDRAW" "INSERT" M "1200,800" 1 1 0 "")))
    ;  (SETQ EL (ENDLAST))
    ;  (ENTDEL EL)))
     ; (SETQ Y (100+Y)))
   ;    (SETQ ABC (100+ABC)))

      (IF (AND (AND (> X 3) (<= X 6)) (= Y 0))
      (PROGN
        (SETQ A1 (STRCAT "M03-" OO AA QQ))
        (SETQ B1 (STRCAT "M04-" OO BB QQ))
        (SETQ C1 (STRCAT "M05-" OO CC QQ))
        (SETQ D1 (STRCAT "M06-" OO DD QQ))
        (SETQ E1 (STRCAT "M08-" OO EE QQ))
        (SETQ F1 (STRCAT "M10-" OO FF QQ))
        (SETQ G1 (STRCAT "M12-" OO GG QQ))
        (SETQ H1 (STRCAT "M14-" OO HH QQ))
        (SETQ I1 (STRCAT "M16-" OO II QQ))
        (SETQ J1 (STRCAT "M20-" OO JJ QQ))
        (SETQ K1 (STRCAT "M24-" OO KK QQ))
        (SETQ L1 (STRCAT "M30-" OO LL QQ))
        (SETQ M1 (STRCAT "M36-" OO MM QQ))
      (COMMAND "REDRAW" "INSERT" A1 "1200,800" 1 1 0 "")
      (COMMAND "REDRAW" "INSERT" B1 "1200,800" 1 1 0 "")
      (COMMAND "REDRAW" "INSERT" C1 "1200,800" 1 1 0 "")
      (COMMAND "REDRAW" "INSERT" D1 "1200,800" 1 1 0 "")
      (COMMAND "REDRAW" "INSERT" E1 "1200,800" 1 1 0 "")
      (COMMAND "REDRAW" "INSERT" F1 "1200,800" 1 1 0 "")
      (COMMAND "REDRAW" "INSERT" G1 "1200,800" 1 1 0 "")
      (COMMAND "REDRAW" "INSERT" H1 "1200,800" 1 1 0 "")
      (COMMAND "REDRAW" "INSERT" I1 "1200,800" 1 1 0 "")
      (COMMAND "REDRAW" "INSERT" J1 "1200,800" 1 1 0 "")
      (COMMAND "REDRAW" "INSERT" K1 "1200,800" 1 1 0 "")
      (COMMAND "REDRAW" "INSERT" L1 "1200,800" 1 1 0 "")
      (COMMAND "REDRAW" "INSERT" M1 "1200,800" 1 1 0 "")))

      (IF (AND (AND (> X 6) (<= X 9)) (= Y 0))
      (PROGN
        (SETQ A2 (STRCAT "M03-" RR AA SS))
        (SETQ B2 (STRCAT "M04-" RR BB SS))
        (SETQ C2 (STRCAT "M05-" RR CC SS))
        (SETQ D2 (STRCAT "M06-" RR DD SS))
        (SETQ E2 (STRCAT "M08-" RR EE SS))
        (SETQ F2 (STRCAT "M10-" RR FF SS))
        (SETQ G2 (STRCAT "M12-" RR GG SS))
        (SETQ H2 (STRCAT "M14-" RR HH SS))
        (SETQ I2 (STRCAT "M16-" RR II SS))
        (SETQ J2 (STRCAT "M20-" RR JJ SS))
        (SETQ K2 (STRCAT "M24-" RR KK SS))
        (SETQ L2 (STRCAT "M30-" RR LL SS))
        (SETQ M2 (STRCAT "M36-" RR MM SS))
      (COMMAND "REDRAW" "INSERT" A2 "1200,800" 1 1 0 "")
      (COMMAND "REDRAW" "INSERT" B2 "1200,800" 1 1 0 "")
      (COMMAND "REDRAW" "INSERT" C2 "1200,800" 1 1 0 "")
      (COMMAND "REDRAW" "INSERT" D2 "1200,800" 1 1 0 "")
      (COMMAND "REDRAW" "INSERT" E2 "1200,800" 1 1 0 "")
      (COMMAND "REDRAW" "INSERT" F2 "1200,800" 1 1 0 "")
      (COMMAND "REDRAW" "INSERT" G2 "1200,800" 1 1 0 "")
      (COMMAND "REDRAW" "INSERT" H2 "1200,800" 1 1 0 "")
      (COMMAND "REDRAW" "INSERT" I2 "1200,800" 1 1 0 "")
      (COMMAND "REDRAW" "INSERT" J2 "1200,800" 1 1 0 "")
      (COMMAND "REDRAW" "INSERT" K2 "1200,800" 1 1 0 "")
      (COMMAND "REDRAW" "INSERT" L2 "1200,800" 1 1 0 "")
      (COMMAND "REDRAW" "INSERT" M2 "1200,800" 1 1 0 "")))

      (IF (AND (AND (> X 9) (<= X 12)) (= Y 0))
      (PROGN
        (SETQ A3 (STRCAT "M03-" RR AA TT))
        (SETQ B3 (STRCAT "M04-" RR BB TT))
        (SETQ C3 (STRCAT "M05-" RR CC TT))
        (SETQ D3 (STRCAT "M06-" RR DD TT))
        (SETQ E3 (STRCAT "M08-" RR EE TT))
        (SETQ F3 (STRCAT "M10-" RR FF TT))
        (SETQ G3 (STRCAT "M12-" RR GG TT))
        (SETQ H3 (STRCAT "M14-" RR HH TT))
        (SETQ I3 (STRCAT "M16-" RR II TT))
        (SETQ J3 (STRCAT "M20-" RR JJ TT))
        (SETQ K3 (STRCAT "M24-" RR KK TT))
        (SETQ L3 (STRCAT "M30-" RR LL TT))
        (SETQ M3 (STRCAT "M36-" RR MM TT))
      (COMMAND "REDRAW" "INSERT" A3 "1200,800" 1 1 0 "")
      (COMMAND "REDRAW" "INSERT" B3 "1200,800" 1 1 0 "")
      (COMMAND "REDRAW" "INSERT" C3 "1200,800" 1 1 0 "")
      (COMMAND "REDRAW" "INSERT" D3 "1200,800" 1 1 0 "")
      (COMMAND "REDRAW" "INSERT" E3 "1200,800" 1 1 0 "")
      (COMMAND "REDRAW" "INSERT" F3 "1200,800" 1 1 0 "")
      (COMMAND "REDRAW" "INSERT" G3 "1200,800" 1 1 0 "")
      (COMMAND "REDRAW" "INSERT" H3 "1200,800" 1 1 0 "")
      (COMMAND "REDRAW" "INSERT" I3 "1200,800" 1 1 0 "")
      (COMMAND "REDRAW" "INSERT" J3 "1200,800" 1 1 0 "")
      (COMMAND "REDRAW" "INSERT" K3 "1200,800" 1 1 0 "")
      (COMMAND "REDRAW" "INSERT" L3 "1200,800" 1 1 0 "")
      (COMMAND "REDRAW" "INSERT" M3 "1200,800" 1 1 0 "")))

      (IF (AND (= X 1) (= Y 1))
      (COMMAND "REDRAW" "INSERT" "C:/ACAD/BLOCK/M03-C" PAUSE 1 1 0 "" ""))
      (IF (AND (= X 2) (= Y 1))
      (COMMAND "REDRAW" "INSERT" "C:/ACAD/BLOCK/M04-C" PAUSE 1 1 0))
      (IF (AND (= X 3) (= Y 1))
      (COMMAND "REDRAW" "INSERT" "C:/ACAD/BLOCK/M05-C" PAUSE 1 1 0))
      (IF (AND (= X 4) (= Y 1))
      (COMMAND "REDRAW" "INSERT" "C:/ACAD/BLOCK/M06-C" PAUSE 1 1 0))
      (IF (AND (= X 5) (= Y 1))
      (COMMAND "REDRAW" "INSERT" "C:/ACAD/BLOCK/M08-C" PAUSE 1 1 0))
      (IF (AND (= X 6) (= Y 1))
      (COMMAND "REDRAW" "INSERT" "C:/ACAD/BLOCK/M10-C" PAUSE 1 1 0))
      (IF (AND (= X 7) (= Y 1))
      (COMMAND "REDRAW" "INSERT" "C:/ACAD/BLOCK/M12-C" PAUSE 1 1 0))
      (IF (AND (= X 8) (= Y 1))
      (COMMAND "REDRAW" "INSERT" "C:/ACAD/BLOCK/M14-C" PAUSE 1 1 0))
      (IF (AND (= X 9) (= Y 1))
      (COMMAND "REDRAW" "INSERT" "C:/ACAD/BLOCK/M16-C" PAUSE 1 1 0))
      (IF (AND (= X 10) (= Y 1))
      (COMMAND "REDRAW" "INSERT" "C:/ACAD/BLOCK/M20-C" PAUSE 1 1 0))
      (IF (AND (= X 11) (= Y 1))
      (COMMAND "REDRAW" "INSERT" "C:/ACAD/BLOCK/M24-C" PAUSE 1 1 0))
      (IF (AND (= X 12) (= Y 1))
      (COMMAND "REDRAW" "INSERT" "C:/ACAD/BLOCK/M30-C" PAUSE 1 1 0))
      (IF (AND (= X 13) (= Y 1))
      (COMMAND "REDRAW" "INSERT" "C:/ACAD/BLOCK/M36-C" PAUSE 1 1 0))
      (IF (AND (= X 1) (= Y 2))
      (COMMAND "REDRAW" "INSERT" "C:/ACAD/BLOCK/M03-F" PAUSE 1 1 0))
      (IF (AND (= X 2) (= Y 2))
      (COMMAND "REDRAW" "INSERT" "C:/ACAD/BLOCK/M04-F" PAUSE 1 1 0))
      (IF (AND (= X 3) (= Y 2))
      (COMMAND "REDRAW" "INSERT" "C:/ACAD/BLOCK/M05-F" PAUSE 1 1 0))
      (IF (AND (= X 4) (= Y 2))
      (COMMAND "REDRAW" "INSERT" "C:/ACAD/BLOCK/M06-F" PAUSE 1 1 0))
      (IF (AND (= X 5) (= Y 2))
      (COMMAND "REDRAW" "INSERT" "C:/ACAD/BLOCK/M08-F" PAUSE 1 1 0))
      (IF (AND (= X 6) (= Y 2))
      (COMMAND "REDRAW" "INSERT" "C:/ACAD/BLOCK/M10-F" PAUSE 1 1 0))
      (IF (AND (= X 7) (= Y 2))
      (COMMAND "REDRAW" "INSERT" "C:/ACAD/BLOCK/M12-F" PAUSE 1 1 0))
      (IF (AND (= X 8) (= Y 2))
      (COMMAND "REDRAW" "INSERT" "C:/ACAD/BLOCK/M14-F" PAUSE 1 1 0))
      (IF (AND (= X 9) (= Y 2))
      (COMMAND "REDRAW" "INSERT" "C:/ACAD/BLOCK/M16-F" PAUSE 1 1 0))
      (IF (AND (= X 10) (= Y 2))
      (COMMAND "REDRAW" "INSERT" "C:/ACAD/BLOCK/M20-F" PAUSE 1 1 0))
      (IF (AND (= X 11) (= Y 2))
      (COMMAND "REDRAW" "INSERT" "C:/ACAD/BLOCK/M24-F" PAUSE 1 1 0))
      (IF (AND (= X 12) (= Y 2))
      (COMMAND "REDRAW" "INSERT" "C:/ACAD/BLOCK/M30-F" PAUSE 1 1 0))
      (IF (AND (= X 13) (= Y 2))
      (COMMAND "REDRAW" "INSERT" "C:/ACAD/BLOCK/M36-F" PAUSE 1 1 0))
      (IF (AND (= X 1) (= Y 3))
      (COMMAND "REDRAW" "INSERT" "C:/ACAD/BLOCK/M03-E" PAUSE 1 1 0))
      (IF (AND (= X 2) (= Y 3))
      (COMMAND "REDRAW" "INSERT" "C:/ACAD/BLOCK/M04-E" PAUSE 1 1 0))
      (IF (AND (= X 3) (= Y 3))
      (COMMAND "REDRAW" "INSERT" "C:/ACAD/BLOCK/M05-E" PAUSE 1 1 0))
      (IF (AND (= X 4) (= Y 3))
      (COMMAND "REDRAW" "INSERT" "C:/ACAD/BLOCK/M06-E" PAUSE 1 1 0))
      (IF (AND (= X 5) (= Y 3))
      (COMMAND "REDRAW" "INSERT" "C:/ACAD/BLOCK/M08-E" PAUSE 1 1 0))
      (IF (AND (= X 6) (= Y 3))
      (COMMAND "REDRAW" "INSERT" "C:/ACAD/BLOCK/M10-E" PAUSE 1 1 0))
      (IF (AND (= X 7) (= Y 3))
      (COMMAND "REDRAW" "INSERT" "C:/ACAD/BLOCK/M12-E" PAUSE 1 1 0))
      (IF (AND (= X 8) (= Y 3))
      (COMMAND "REDRAW" "INSERT" "C:/ACAD/BLOCK/M14-E" PAUSE 1 1 0))
      (IF (AND (= X 9) (= Y 3))
      (COMMAND "REDRAW" "INSERT" "C:/ACAD/BLOCK/M16-E" PAUSE 1 1 0))
      (IF (AND (= X 10) (= Y 3))
      (COMMAND "REDRAW" "INSERT" "C:/ACAD/BLOCK/M20-E" PAUSE 1 1 0))
      (IF (AND (= X 11) (= Y 3))
      (COMMAND "REDRAW" "INSERT" "C:/ACAD/BLOCK/M24-E" PAUSE 1 1 0))
      (IF (AND (= X 12) (= Y 3))
      (COMMAND "REDRAW" "INSERT" "C:/ACAD/BLOCK/M30-E" PAUSE 1 1 0))
      (IF (AND (= X 13) (= Y 3))
      (COMMAND "REDRAW" "INSERT" "C:/ACAD/BLOCK/M36-E" PAUSE 1 1 0))
      (IF (AND (= X 1) (= Y 4))
      (COMMAND "REDRAW" "INSERT" "C:/ACAD/BLOCK/M03-B" PAUSE 1 1 0))
      (IF (AND (= X 2) (= Y 4))
      (COMMAND "REDRAW" "INSERT" "C:/ACAD/BLOCK/M04-B" PAUSE 1 1 0))
      (IF (AND (= X 3) (= Y 4))
      (COMMAND "REDRAW" "INSERT" "C:/ACAD/BLOCK/M05-B" PAUSE 1 1 0))
      (IF (AND (= X 4) (= Y 4))
      (COMMAND "REDRAW" "INSERT" "C:/ACAD/BLOCK/M06-B" PAUSE 1 1 0))
      (IF (AND (= X 5) (= Y 4))
      (COMMAND "REDRAW" "INSERT" "C:/ACAD/BLOCK/M08-B" PAUSE 1 1 0))
      (IF (AND (= X 6) (= Y 4))
      (COMMAND "REDRAW" "INSERT" "C:/ACAD/BLOCK/M10-B" PAUSE 1 1 0))
      (IF (AND (= X 7) (= Y 4))
      (COMMAND "REDRAW" "INSERT" "C:/ACAD/BLOCK/M12-B" PAUSE 1 1 0))
      (IF (AND (= X 8) (= Y 4))
      (COMMAND "REDRAW" "INSERT" "C:/ACAD/BLOCK/M14-B" PAUSE 1 1 0))
      (IF (AND (= X 9) (= Y 4))
      (COMMAND "REDRAW" "INSERT" "C:/ACAD/BLOCK/M16-B" PAUSE 1 1 0))
      (IF (AND (= X 10) (= Y 4))
      (COMMAND "REDRAW" "INSERT" "C:/ACAD/BLOCK/M20-B" PAUSE 1 1 0))
      (IF (AND (= X 11) (= Y 4))
      (COMMAND "REDRAW" "INSERT" "C:/ACAD/BLOCK/M24-B" PAUSE 1 1 0))
      (IF (AND (= X 12) (= Y 4))
      (COMMAND "REDRAW" "INSERT" "C:/ACAD/BLOCK/M30-B" PAUSE 1 1 0))
      (IF (AND (= X 13) (= Y 4))
      (COMMAND "REDRAW" "INSERT" "C:/ACAD/BLOCK/M36-B" PAUSE 1 1 0))
      (IF (AND (= X 1) (= Y 5))
      (COMMAND "REDRAW" "INSERT" "C:/ACAD/BLOCK/M03-A" PAUSE 1 1 0))
      (IF (AND (= X 2) (= Y 5))
      (COMMAND "REDRAW" "INSERT" "C:/ACAD/BLOCK/M04-A" PAUSE 1 1 0))
      (IF (AND (= X 3) (= Y 5))
      (COMMAND "REDRAW" "INSERT" "C:/ACAD/BLOCK/M05-A" PAUSE 1 1 0))
      (IF (AND (= X 4) (= Y 5))
      (COMMAND "REDRAW" "INSERT" "C:/ACAD/BLOCK/M06-A" PAUSE 1 1 0))
      (IF (AND (= X 5) (= Y 5))
      (COMMAND "REDRAW" "INSERT" "C:/ACAD/BLOCK/M08-A" PAUSE 1 1 0))
      (IF (AND (= X 6) (= Y 5))
      (COMMAND "REDRAW" "INSERT" "C:/ACAD/BLOCK/M10-A" PAUSE 1 1 0))
      (IF (AND (= X 7) (= Y 5))
      (COMMAND "REDRAW" "INSERT" "C:/ACAD/BLOCK/M12-A" PAUSE 1 1 0))
      (IF (AND (= X 8) (= Y 5))
      (COMMAND "REDRAW" "INSERT" "C:/ACAD/BLOCK/M14-A" PAUSE 1 1 0))
      (IF (AND (= X 9) (= Y 5))
      (COMMAND "REDRAW" "INSERT" "C:/ACAD/BLOCK/M16-A" PAUSE 1 1 0))
      (IF (AND (= X 10) (= Y 5))
      (COMMAND "REDRAW" "INSERT" "C:/ACAD/BLOCK/M20-A" PAUSE 1 1 0))
      (IF (AND (= X 11) (= Y 5))
      (COMMAND "REDRAW" "INSERT" "C:/ACAD/BLOCK/M24-A" PAUSE 1 1 0))
      (IF (AND (= X 12) (= Y 5))
      (COMMAND "REDRAW" "INSERT" "C:/ACAD/BLOCK/M30-A" PAUSE 1 1 0))
      (IF (AND (= X 13) (= Y 5))
      (COMMAND "REDRAW" "INSERT" "C:/ACAD/BLOCK/M36-A" PAUSE 1 1 0))
      (IF (AND (= X 1) (= Y 6))
      (COMMAND "REDRAW" "INSERT" "C:/ACAD/BLOCK/M03-D" PAUSE 1 1 0))
      (IF (AND (= X 2) (= Y 6))
      (COMMAND "REDRAW" "INSERT" "C:/ACAD/BLOCK/M04-D" PAUSE 1 1 0))
      (IF (AND (= X 3) (= Y 6))
      (COMMAND "REDRAW" "INSERT" "C:/ACAD/BLOCK/M05-D" PAUSE 1 1 0))
      (IF (AND (= X 4) (= Y 6))
      (COMMAND "REDRAW" "INSERT" "C:/ACAD/BLOCK/M06-D" PAUSE 1 1 0))
      (IF (AND (= X 5) (= Y 6))
      (COMMAND "REDRAW" "INSERT" "C:/ACAD/BLOCK/M08-D" PAUSE 1 1 0))
      (IF (AND (= X 6) (= Y 6))
      (COMMAND "REDRAW" "INSERT" "C:/ACAD/BLOCK/M10-D" PAUSE 1 1 0))
      (IF (AND (= X 7) (= Y 6))
      (COMMAND "REDRAW" "INSERT" "C:/ACAD/BLOCK/M12-D" PAUSE 1 1 0))
      (IF (AND (= X 8) (= Y 6))
      (COMMAND "REDRAW" "INSERT" "C:/ACAD/BLOCK/M14-D" PAUSE 1 1 0))
      (IF (AND (= X 9) (= Y 6))
      (COMMAND "REDRAW" "INSERT" "C:/ACAD/BLOCK/M16-D" PAUSE 1 1 0))
      (IF (AND (= X 10) (= Y 6))
      (COMMAND "REDRAW" "INSERT" "C:/ACAD/BLOCK/M20-D" PAUSE 1 1 0))
      (IF (AND (= X 11) (= Y 6))
      (COMMAND "REDRAW" "INSERT" "C:/ACAD/BLOCK/M24-D" PAUSE 1 1 0))
      (IF (AND (= X 12) (= Y 6))
      (COMMAND "REDRAW" "INSERT" "C:/ACAD/BLOCK/M30-D" PAUSE 1 1 0))
      (IF (AND (= X 13) (= Y 6))
      (COMMAND "REDRAW" "INSERT" "C:/ACAD/BLOCK/M36-D" PAUSE 1 1 0))
      (COMMAND "LAYER" "S" CY ""))

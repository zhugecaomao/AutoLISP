(DEFUN C:SCREW1 ()
   (SETVAR "CMDECHO" 0)
   (SETQ VC (GETVAR "VIEWCTR"))
   (SETQ YR (GETVAR "VIEWSIZE"))
   (SETQ XR (* YR 1.3864))
   (SETQ YD (/ YR 4))
   (SETQ XD (/ XR 8))
   (SETQ XB (- (CAR VC) (/ XR 2)))
   (SETQ YB (- (CADR VC) (/ YR 2)))
   (COMMAND "VSLIDE" "C:/ACAD/SLIDE/SCREW1")
;----
   (SETQ PT (GETPOINT "\nPLEASE DIGIT THE CHAR. TABLE : "))
             (SETQ XP (CAR PT))
             (SETQ YP (CADR PT))
             (SETQ XAA (- XP XB))
             (SETQ YAA (- YP YB))
             (SETQ XA (ABS XAA))
             (SETQ YA (ABS YAA))
             (SETQ X (FIX ( / XA XD)))
             (SETQ Y (FIX ( / YA YD)))
;
      (IF (AND (= X 0) (= Y 0))
      (COMMAND "REDRAW" "INSERT" "C:/ACAD/BLOCK/M16-1" PAUSE 1 1))
      (IF (AND (= X 1) (= Y 0))
      (COMMAND "REDRAW" "INSERT" "C:/ACAD/BLOCK/M20-1" PAUSE 1 1))
      (IF (AND (= X 2) (= Y 0))
      (COMMAND "REDRAW" "INSERT" "C:/ACAD/BLOCK/M24-1" PAUSE 1 1))
      (IF (AND (= X 3) (= Y 0))
      (COMMAND "REDRAW" "INSERT" "C:/ACAD/BLOCK/M30-1" PAUSE 1 1))
      (IF (AND (= X 4) (= Y 0))
      (COMMAND "REDRAW" "INSERT" "C:/ACAD/BLOCK/M36-1" PAUSE 1 1))
      (IF (AND (= X 5) (= Y 0))
      (COMMAND "REDRAW" "INSERT" "C:/ACAD/BLOCK/M42-1" PAUSE 1 1))
      (IF (AND (= X 6) (= Y 0))
      (COMMAND "REDRAW" "INSERT" "C:/ACAD/BLOCK/M48-1" PAUSE 1 1))
      (IF (AND (= X 0) (= Y 1))
      (COMMAND "REDRAW" "INSERT" "C:/ACAD/BLOCK/M16" PAUSE 1 1))
      (IF (AND (= X 1) (= Y 1))
      (COMMAND "REDRAW" "INSERT" "C:/ACAD/BLOCK/M20" PAUSE 1 1))
      (IF (AND (= X 2) (= Y 1))
      (COMMAND "REDRAW" "INSERT" "C:/ACAD/BLOCK/M24" PAUSE 1 1))
      (IF (AND (= X 3) (= Y 1))
      (COMMAND "REDRAW" "INSERT" "C:/ACAD/BLOCK/M30" PAUSE 1 1))
      (IF (AND (= X 4) (= Y 1))
      (COMMAND "REDRAW" "INSERT" "C:/ACAD/BLOCK/M36" PAUSE 1 1))
      (IF (AND (= X 5) (= Y 1))
      (COMMAND "REDRAW" "INSERT" "C:/ACAD/BLOCK/M42" PAUSE 1 1))
      (IF (AND (= X 6) (= Y 1))
      (COMMAND "REDRAW" "INSERT" "C:/ACAD/BLOCK/M48" PAUSE 1 1))
      (IF (AND (= X 0) (= Y 2))
      (COMMAND "REDRAW" "INSERT" "C:/ACAD/BLOCK/M03-1" PAUSE 1 1))
      (IF (AND (= X 1) (= Y 2))
      (COMMAND "REDRAW" "INSERT" "C:/ACAD/BLOCK/M04-1" PAUSE 1 1))
      (IF (AND (= X 2) (= Y 2))
      (COMMAND "REDRAW" "INSERT" "C:/ACAD/BLOCK/M05-1" PAUSE 1 1))
      (IF (AND (= X 3) (= Y 2))
      (COMMAND "REDRAW" "INSERT" "C:/ACAD/BLOCK/M06-1" PAUSE 1 1))
      (IF (AND (= X 4) (= Y 2))
      (COMMAND "REDRAW" "INSERT" "C:/ACAD/BLOCK/M08-1" PAUSE 1 1))
      (IF (AND (= X 5) (= Y 2))
      (COMMAND "REDRAW" "INSERT" "C:/ACAD/BLOCK/M10-1" PAUSE 1 1))
      (IF (AND (= X 6) (= Y 2))
      (COMMAND "REDRAW" "INSERT" "C:/ACAD/BLOCK/M12-1" PAUSE 1 1))
      (IF (AND (= X 7) (= Y 2))
      (COMMAND "REDRAW" "INSERT" "C:/ACAD/BLOCK/M14-1" PAUSE 1 1))
      (IF (AND (= X 0) (= Y 3))
      (COMMAND "REDRAW" "INSERT" "C:/ACAD/BLOCKM03" PAUSE 1 1))
      (IF (AND (= X 1) (= Y 3))
      (COMMAND "REDRAW" "INSERT" "C:/ACAD/BLOCK/M04" PAUSE 1 1))
      (IF (AND (= X 2) (= Y 3))
      (COMMAND "REDRAW" "INSERT" "C:/ACAD/BLOCK/M05" PAUSE 1 1))
      (IF (AND (= X 3) (= Y 3))
      (COMMAND "REDRAW" "INSERT" "C:/ACAD/BLOCK/M06" PAUSE 1 1))
      (IF (AND (= X 4) (= Y 3))
      (COMMAND "REDRAW" "INSERT" "C:/ACAD/BLOCK/M08" PAUSE 1 1))
      (IF (AND (= X 5) (= Y 3))
      (COMMAND "REDRAW" "INSERT" "C:/ACAD/BLOCK/M10" PAUSE 1 1))
      (IF (AND (= X 6) (= Y 3))
      (COMMAND "REDRAW" "INSERT" "C:/ACAD/BLOCK/M12" PAUSE 1 1))
      (IF (AND (= X 7) (= Y 3))
      (COMMAND "REDRAW" "INSERT" "C:/ACAD/BLOCK/M14" PAUSE 1 1))
      )

(DEFUN C:SCREW2 ()
   (SETVAR "CMDECHO" 0)
   (SETQ VC (GETVAR "VIEWCTR"))
   (SETQ YR (GETVAR "VIEWSIZE"))
   (SETQ XR (* YR 1.3864))
   (SETQ YD (/ YR 4))
   (SETQ XD (/ XR 11))
   (SETQ XB (- (CAR VC) (/ XR 2)))
   (SETQ YB (- (CADR VC) (/ YR 2)))
   (COMMAND "VSLIDE" "C:/ACAD/SLIDE/SCREW2")
;----
  (SETQ PT (GETPOINT "\nPLEASE DIGIT THE CHAR. TABLE : "))
           (SETQ XP (CAR PT))
           (SETQ YP (CADR PT))
           (SETQ XAA (- XP XB))
           (SETQ YAA (- YP YB))
           (SETQ XA (ABS XAA))
           (SETQ YA (ABS YAA))
            (SETQ X (FIX ( / XA XD)))
            (SETQ Y (FIX ( / YA YD)))
;
     (IF (AND (= X 1) (= Y 0))
     (COMMAND "REDRAW" "INSERT" "C:/ACAD/BLOCK/M03-L" PAUSE 1 1 0))
     (IF (AND (= X 2) (= Y 0))
     (COMMAND "REDRAW" "INSERT" "C:/ACAD/BLOCK/M04-L" PAUSE 1 1 0))
     (IF (AND (= X 3) (= Y 0))
     (COMMAND "REDRAW" "INSERT" "C:/ACAD/BLOCK/M05-L" PAUSE 1 1 0))
     (IF (AND (= X 4) (= Y 0))
     (COMMAND "REDRAW" "INSERT" "C:/ACAD/BLOCK/M06-L" PAUSE 1 1 0))
     (IF (AND (= X 5) (= Y 0))
     (COMMAND "REDRAW" "INSERT" "C:/ACAD/BLOCK/M08-L" PAUSE 1 1 0))
     (IF (AND (= X 6) (= Y 0))
     (COMMAND "REDRAW" "INSERT" "C:/ACAD/BLOCK/M10-L" PAUSE 1 1 0))
     (IF (AND (= X 7) (= Y 0))
     (COMMAND "REDRAW" "INSERT" "C:/ACAD/BLOCK/M12-L" PAUSE 1 1 0))
     (IF (AND (= X 8) (= Y 0))
     (COMMAND "REDRAW" "INSERT" "C:/ACAD/BLOCK/M14-L" PAUSE 1 1 0))
     (IF (AND (= X 9) (= Y 0))
     (COMMAND "REDRAW" "INSERT" "C:/ACAD/BLOCK/M16-L" PAUSE 1 1 0))
     (IF (AND (= X 10) (= Y 0))
     (COMMAND "REDRAW" "INSERT" "C:/ACAD/BLOCK/M20-L" PAUSE 1 1 0))
     (IF (AND (= X 1) (= Y 1))
     (COMMAND "REDRAW" "INSERT" "C:/ACAD/BLOCK/M03-K" PAUSE 1 1 0))
     (IF (AND (= X 2) (= Y 1))
     (COMMAND "REDRAW" "INSERT" "C:/ACAD/BLOCK/M04-K" PAUSE 1 1 0))
     (IF (AND (= X 3) (= Y 1))
     (COMMAND "REDRAW" "INSERT" "C:/ACAD/BLOCK/M05-K" PAUSE 1 1 0))
     (IF (AND (= X 4) (= Y 1))
     (COMMAND "REDRAW" "INSERT" "C:/ACAD/BLOCK/M06-K" PAUSE 1 1 0))
     (IF (AND (= X 5) (= Y 1))
     (COMMAND "REDRAW" "INSERT" "C:/ACAD/BLOCK/M08-K" PAUSE 1 1 0))
     (IF (AND (= X 6) (= Y 1))
     (COMMAND "REDRAW" "INSERT" "C:/ACAD/BLOCK/M10-K" PAUSE 1 1 0))
     (IF (AND (= X 7) (= Y 1))
     (COMMAND "REDRAW" "INSERT" "C:/ACAD/BLOCK/M12-K" PAUSE 1 1 0))
     (IF (AND (= X 8) (= Y 1))
     (COMMAND "REDRAW" "INSERT" "C:/ACAD/BLOCK/M14-K" PAUSE 1 1 0))
     (IF (AND (= X 9) (= Y 1))
     (COMMAND "REDRAW" "INSERT" "C:/ACAD/BLOCK/M16-K" PAUSE 1 1 0))
     (IF (AND (= X 10) (= Y 1))
     (COMMAND "REDRAW" "INSERT" "C:/ACAD/BLOCK/M20-K" PAUSE 1 1 0))
     (IF (AND (= X 1) (= Y 2))
     (COMMAND "REDRAW" "INSERT" "C:/ACAD/BLOCK/M03-H" PAUSE 1 1 0))
     (IF (AND (= X 2) (= Y 2))
     (COMMAND "REDRAW" "INSERT" "C:/ACAD/BLOCK/M04-H" PAUSE 1 1 0))
     (IF (AND (= X 3) (= Y 2))
     (COMMAND "REDRAW" "INSERT" "C:/ACAD/BLOCK/M05-H" PAUSE 1 1 0))
     (IF (AND (= X 4) (= Y 2))
     (COMMAND "REDRAW" "INSERT" "C:/ACAD/BLOCK/M06-H" PAUSE 1 1 0))
     (IF (AND (= X 5) (= Y 2))
     (COMMAND "REDRAW" "INSERT" "C:/ACAD/BLOCK/M08-H" PAUSE 1 1 0))
     (IF (AND (= X 6) (= Y 2))
     (COMMAND "REDRAW" "INSERT" "C:/ACAD/BLOCK/M10-H" PAUSE 1 1 0))
     (IF (AND (= X 7) (= Y 2))
     (COMMAND "REDRAW" "INSERT" "C:/ACAD/BLOCK/M12-H" PAUSE 1 1 0))
     (IF (AND (= X 8) (= Y 2))
     (COMMAND "REDRAW" "INSERT" "C:/ACAD/BLOCK/M14-H" PAUSE 1 1 0))
     (IF (AND (= X 9) (= Y 2))
     (COMMAND "REDRAW" "INSERT" "C:/ACAD/BLOCK/M16-H" PAUSE 1 1 0))
     (IF (AND (= X 10) (= Y 2))
     (COMMAND "REDRAW" "INSERT" "C:/ACAD/BLOCK/M20-H" PAUSE 1 1 0))
     (IF (AND (= X 1) (= Y 3))
     (COMMAND "REDRAW" "INSERT" "C:/ACAD/BLOCK/M03-G" PAUSE 1 1 0))
     (IF (AND (= X 2) (= Y 3))
     (COMMAND "REDRAW" "INSERT" "C:/ACAD/BLOCK/M04-G" PAUSE 1 1 0))
     (IF (AND (= X 3) (= Y 3))
     (COMMAND "REDRAW" "INSERT" "C:/ACAD/BLOCK/M05-G" PAUSE 1 1 0))
     (IF (AND (= X 4) (= Y 3))
     (COMMAND "REDRAW" "INSERT" "C:/ACAD/BLOCK/M06-G" PAUSE 1 1 0))
     (IF (AND (= X 5) (= Y 3))
     (COMMAND "REDRAW" "INSERT" "C:/ACAD/BLOCK/M08-G" PAUSE 1 1 0))
     (IF (AND (= X 6) (= Y 3))
     (COMMAND "REDRAW" "INSERT" "C:/ACAD/BLOCK/M10-G" PAUSE 1 1 0))
     (IF (AND (= X 7) (= Y 3))
     (COMMAND "REDRAW" "INSERT" "C:/ACAD/BLOCK/M12-G" PAUSE 1 1 0))
     (IF (AND (= X 8) (= Y 3))
     (COMMAND "REDRAW" "INSERT" "C:/ACAD/BLOCK/M14-G" PAUSE 1 1 0))
     (IF (AND (= X 9) (= Y 3))
     (COMMAND "REDRAW" "INSERT" "C:/ACAD/BLOCK/M16-G" PAUSE 1 1 0))
     (IF (AND (= X 10) (= Y 3))
     (COMMAND "REDRAW" "INSERT" "C:/ACAD/BLOCK/M20-G" PAUSE 1 1 0))
     )

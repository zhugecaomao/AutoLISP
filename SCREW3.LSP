(DEFUN C:SCREW3 ()
   (SETVAR "CMDECHO" 0)
   (SETQ VC (GETVAR "VIEWCTR"))
   (SETQ YR (GETVAR "VIEWSIZE"))
   (SETQ XR (* YR 1.3864))
   (SETQ YD (/ YR 4))
   (SETQ XD (/ XR 11))
   (SETQ XB (- (CAR VC) (/ XR 2)))
   (SETQ YB (- (CADR VC) (/ YR 2)))
   (COMMAND "VSLIDE" "C:/ACAD/SLIDE/SCREW3")
;----
  (SETQ PT (GETPOINT "\nPLEASE DIGIT THE CHAR. TABLE : "))
           (SETQ XP (CAR PT))
           (SETQ YP (CADR PT))
           (SETQ XAA (- XP XB))
           (SETQ YAA (- YP YB))
           (SETQ XA (ABS XAA))
           (SETQ YA (ABS YAA))
            (SETQ X (FIX ( / XA XD)))
            (SETQ Y (FIX ( / YA YD)))
;
     (IF (AND (= X 1) (= Y 0))
     (COMMAND "REDRAW" "INSERT" "C:/ACAD/BLOCK/M03-N" PAUSE 1 1 0))
     (IF (AND (= X 2) (= Y 0))
     (COMMAND "REDRAW" "INSERT" "C:/ACAD/BLOCK/M04-N" PAUSE 1 1 0))
     (IF (AND (= X 3) (= Y 0))
     (COMMAND "REDRAW" "INSERT" "C:/ACAD/BLOCK/M05-N" PAUSE 1 1 0))
     (IF (AND (= X 4) (= Y 0))
     (COMMAND "REDRAW" "INSERT" "C:/ACAD/BLOCK/M06-N" PAUSE 1 1 0))
     (IF (AND (= X 5) (= Y 0))
     (COMMAND "REDRAW" "INSERT" "C:/ACAD/BLOCK/M08-N" PAUSE 1 1 0))
     (IF (AND (= X 6) (= Y 0))
     (COMMAND "REDRAW" "INSERT" "C:/ACAD/BLOCK/M10-N" PAUSE 1 1 0))
     (IF (AND (= X 7) (= Y 0))
     (COMMAND "REDRAW" "INSERT" "C:/ACAD/BLOCK/M12-N" PAUSE 1 1 0))
     (IF (AND (= X 8) (= Y 0))
     (COMMAND "REDRAW" "INSERT" "C:/ACAD/BLOCK/M14-N" PAUSE 1 1 0))
     (IF (AND (= X 9) (= Y 0))
     (COMMAND "REDRAW" "INSERT" "C:/ACAD/BLOCK/M16-N" PAUSE 1 1 0))
     (IF (AND (= X 10) (= Y 0))
     (COMMAND "REDRAW" "INSERT" "C:/ACAD/BLOCK/M20-N" PAUSE 1 1 0))
     (IF (AND (= X 1) (= Y 1))
     (COMMAND "REDRAW" "INSERT" "C:/ACAD/BLOCK/M03-M" PAUSE 1 1 0))
     (IF (AND (= X 2) (= Y 1))
     (COMMAND "REDRAW" "INSERT" "C:/ACAD/BLOCK/M04-M" PAUSE 1 1 0))
     (IF (AND (= X 3) (= Y 1))
     (COMMAND "REDRAW" "INSERT" "C:/ACAD/BLOCK/M05-M" PAUSE 1 1 0))
     (IF (AND (= X 4) (= Y 1))
     (COMMAND "REDRAW" "INSERT" "C:/ACAD/BLOCK/M06-M" PAUSE 1 1 0))
     (IF (AND (= X 5) (= Y 1))
     (COMMAND "REDRAW" "INSERT" "C:/ACAD/BLOCK/M08-M" PAUSE 1 1 0))
     (IF (AND (= X 6) (= Y 1))
     (COMMAND "REDRAW" "INSERT" "C:/ACAD/BLOCK/M10-M" PAUSE 1 1 0))
     (IF (AND (= X 7) (= Y 1))
     (COMMAND "REDRAW" "INSERT" "C:/ACAD/BLOCK/M12-M" PAUSE 1 1 0))
     (IF (AND (= X 8) (= Y 1))
     (COMMAND "REDRAW" "INSERT" "C:/ACAD/BLOCK/M14-M" PAUSE 1 1 0))
     (IF (AND (= X 9) (= Y 1))
     (COMMAND "REDRAW" "INSERT" "C:/ACAD/BLOCK/M16-M" PAUSE 1 1 0))
     (IF (AND (= X 10) (= Y 1))
     (COMMAND "REDRAW" "INSERT" "C:/ACAD/BLOCK/M20-M" PAUSE 1 1 0))
     (IF (AND (= X 1) (= Y 2))
     (COMMAND "REDRAW" "INSERT" "C:/ACAD/BLOCK/M03-J" PAUSE 1 1 0))
     (IF (AND (= X 2) (= Y 2))
     (COMMAND "REDRAW" "INSERT" "C:/ACAD/BLOCK/M04-J" PAUSE 1 1 0))
     (IF (AND (= X 3) (= Y 2))
     (COMMAND "REDRAW" "INSERT" "C:/ACAD/BLOCK/M05-J" PAUSE 1 1 0))
     (IF (AND (= X 4) (= Y 2))
     (COMMAND "REDRAW" "INSERT" "C:/ACAD/BLOCK/M06-J" PAUSE 1 1 0))
     (IF (AND (= X 5) (= Y 2))
     (COMMAND "REDRAW" "INSERT" "C:/ACAD/BLOCK/M08-J" PAUSE 1 1 0))
     (IF (AND (= X 6) (= Y 2))
     (COMMAND "REDRAW" "INSERT" "C:/ACAD/BLOCK/M10-J" PAUSE 1 1 0))
     (IF (AND (= X 7) (= Y 2))
     (COMMAND "REDRAW" "INSERT" "C:/ACAD/BLOCK/M12-J" PAUSE 1 1 0))
     (IF (AND (= X 8) (= Y 2))
     (COMMAND "REDRAW" "INSERT" "C:/ACAD/BLOCK/M14-J" PAUSE 1 1 0))
     (IF (AND (= X 9) (= Y 2))
     (COMMAND "REDRAW" "INSERT" "C:/ACAD/BLOCK/M16-J" PAUSE 1 1 0))
     (IF (AND (= X 10) (= Y 2))
     (COMMAND "REDRAW" "INSERT" "C:/ACAD/BLOCK/M20-J" PAUSE 1 1 0))
     (IF (AND (= X 1) (= Y 3))
     (COMMAND "REDRAW" "INSERT" "C:/ACAD/BLOCK/M03-I" PAUSE 1 1 0))
     (IF (AND (= X 2) (= Y 3))
     (COMMAND "REDRAW" "INSERT" "C:/ACAD/BLOCK/M04-I" PAUSE 1 1 0))
     (IF (AND (= X 3) (= Y 3))
     (COMMAND "REDRAW" "INSERT" "C:/ACAD/BLOCK/M05-I" PAUSE 1 1 0))
     (IF (AND (= X 4) (= Y 3))
     (COMMAND "REDRAW" "INSERT" "C:/ACAD/BLOCK/M06-I" PAUSE 1 1 0))
     (IF (AND (= X 5) (= Y 3))
     (COMMAND "REDRAW" "INSERT" "C:/ACAD/BLOCK/M08-I" PAUSE 1 1 0))
     (IF (AND (= X 6) (= Y 3))
     (COMMAND "REDRAW" "INSERT" "C:/ACAD/BLOCK/M10-I" PAUSE 1 1 0))
     (IF (AND (= X 7) (= Y 3))
     (COMMAND "REDRAW" "INSERT" "C:/ACAD/BLOCK/M12-I" PAUSE 1 1 0))
     (IF (AND (= X 8) (= Y 3))
     (COMMAND "REDRAW" "INSERT" "C:/ACAD/BLOCK/M14-I" PAUSE 1 1 0))
     (IF (AND (= X 9) (= Y 3))
     (COMMAND "REDRAW" "INSERT" "C:/ACAD/BLOCK/M16-I" PAUSE 1 1 0))
     (IF (AND (= X 10) (= Y 3))
     (COMMAND "REDRAW" "INSERT" "C:/ACAD/BLOCK/M20-I" PAUSE 1 1 0))
     )

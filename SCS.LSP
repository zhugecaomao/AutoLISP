(defun c:scs ()
(prompt "select souce style")
(setq ba (cdr (entget (car (entsel)))))
(setq ba2 (assoc 10 ba))
(setq ba1 (assoc 1 ba))
(prompt "select to change style")
(setq sa (ssget))
(setq sl (sslength sa))
(setq n 0)
(repeat sl
(setq c (ssname sa n))
(setq d (car (entget c)))
(setq e (cdr (entget c)))
(setq f1 (assoc 10 e))
(setq f (assoc 1 e))
(setq g (subst f ba1 ba))
(setq g1 (subst f1 ba2 g))
(setq i (cdr (assoc 0 e)))
(if (= i "TEXT")
(PROGN
(setq h (cons d g1 ))
(entmod h)
))
(setq n (+ n 1))
)
(princ)
)

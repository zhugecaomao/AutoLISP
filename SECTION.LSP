(DEFUN C:section()
(setq F (getvar "blipmode")) (setvar "blipmode" 0)
(setq G(getvar "clayer"))
(setq H2(getvar "dimscale"))
(setq H1(getvar "dimtxt"))
(setq H (* H1 H2))
(command "linetype" "s" "phantom" "")
(setq E(getstring "\n Enter section name:"))
(setq P1(getpoint "\n Enter 1st point:"))
(command "line" P1 pause "")
(setq P2(getvar "lastpoint"))
(setq P3(polar P1 (- (angle P1 P2) (/ pi 2)) (* H 0.75)))
(setq P4(polar P1 (+ (angle P1 P2) (/ pi 2)) 0.1))
(setq P5(polar P3 (- (angle P1 P2) (/ pi 2)) (/ H 2.0)))
(setq P6 (polar P1 (- (angle P1 P2) (/ pi 2)) 0.1))
(setq P7(polar P1 (- (angle P1 P2) (/ pi 2)) (* H 2.0)))
(command "linetype" "s" "bylayer" "")
(command "pline" P4 "w" H H P6 "w" 0 (/ H 4.0) P3 "w" 0 0 P5 "")
(command "copy" "L" "" P1 P2)
(command "text" "m" P7 H 0 E)
(command "copy" "L" "" P1 P2)
(setvar "blipmode" F))

(defun C:SEQ()
     (setvar "cmdecho" 0)
     (setq a (getvar "snapang"))
     (setq b (getvar "orthomode"))
     (setq p1 (getpoint "\nFrom point: "))
     (setq p2 (getpoint P1 "\nTo point: "))
     (command "line" p1 p2 "")
     (setvar "snapang" (angle p1 p2))
     (setvar "orthomode" 1)
     (setq p3 (getpoint p2 "\nTo point: "))
     (setq p4 (polar p3 (angle p2 p1)
		(distance p2 p1)))
  (command "line" p2 p3 p4 p1 "")
     (setvar "snapang" a)
     (setvar "orthomode" b)
)

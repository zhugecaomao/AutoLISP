DEFUN C:SET4
;SET LAYER
(COMMAND "SETVAR" "CMDECHO" 0)
;(IF (= (TYPE F1) 'FILE ) "YES"  (STOP))
;(IF (= (TYPE F2) 'FILE ) "YES" (STOP))
(setq SET4 (findfile "/ACAD/HON/SET/SET4.SET"))
(IF (= SET4 NIL)
    (PROGN
       (PROMPT "\nPLEASE SETTING LAYER:" )
       (SETQ FC (OPEN "/ACAD/HON/SET/SET4.SET" "w"))
       (setq SETL4 (GETSTRING T"\nSETTING LAYER ? <4>:"))
       (IF (OR (= SETL4 "") (= SETL4 NIL))
              (WRITE-LINE "4" FC)
              (WRITE-LINE SETL4 FC)
       )
       (CLOSE FC)
    )
)

(IF (/= SET4 NIL)
    (PROGN
       (SETQ FC (OPEN "/ACAD/HON/SET/SET4.SET" "r"))
       (SETQ SETL4 (READ-LINE FC))
       (IF (OR (= SETL4 "") (= SETL4 NIL))
           (CLOSE FC)
       )
       (IF (OR (= SETL4 "") (= SETL4 NIL))
           (PROGN
              (PROMPT "\nPLEASE SETTING LAYER:" )
              (SETQ FC (OPEN "/ACAD/HON/SET/SET4.SET" "w"))
              (setq SETL4 (GETSTRING T"\nSETTING LAYER ? <4>:"))
              (IF (= SETL4 "")
                  (WRITE-LINE "4" FC)
                  (WRITE-LINE SETL4 FC)
              )
           (CLOSE FC)
           )
       )
       (SETQ FC (OPEN "/ACAD/HON/SET/SET4.SET" "r"))
       (SETQ SETL4 (READ-LINE FC))
       (CLOSE FC)
       (PROMPT "\nLAYER NAME IS:" )(PROMPT SETL4)(TERPRI)
    )
)

(SETQ ANS (strcase (GETSTRING "\nDO YOU WANT TO CHANGE LAST SETTING <Y/N> N:")))
(IF (= ANS "Y")
    (PROGN
       (PROMPT "\nPLEASE SETTING LAYER:" )
       (SETQ FC (OPEN "/ACAD/HON/SET/SET4.SET" "w"))
       (PROMPT "\nLAYER IS " )(PROMPT "<")(PROMPT SETL4) (PROMPT ">:")
       (SETQ SETW4 SETL4)
       (setq SETL4 (GETSTRING T))
       (IF (OR (= SETL4 "") (= SETL4 NIL))
               (WRITE-LINE SETW4 FC)
               (WRITE-LINE SETL4 FC)
       )
       (CLOSE FC)
       (SETQ FC (OPEN "/ACAD/HON/SET/SET4.SET" "r"))
       (SETQ SETL4 (READ-LINE FC))
       (CLOSE FC)
       (PROMPT "\nLAYER NOW IS:" )(PROMPT SETL4)(TERPRI)
  )
)

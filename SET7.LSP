DEFUN C:SET7
;SET LAYER
(COMMAND "SETVAR" "CMDECHO" 0)
;(IF (= (TYPE F1) 'FILE ) "YES"  (STOP))
;(IF (= (TYPE F2) 'FILE ) "YES" (STOP))
(setq SET7 (findfile "/ACAD/HON/SET/SET7.SET"))
(IF (= SET7 NIL)
    (PROGN
       (PROMPT "\nPLEASE SETTING LAYER:" )
       (SETQ FC (OPEN "/ACAD/HON/SET/SET7.SET" "w"))
       (setq SETL7 (GETSTRING T"\nSETTING LAYER ? <7>:"))
       (IF (OR (= SETL7 "") (= SETL7 NIL))
              (WRITE-LINE "7" FC)
              (WRITE-LINE SETL7 FC)
       )
       (CLOSE FC)
    )
)

(IF (/= SET7 NIL)
    (PROGN
       (SETQ FC (OPEN "/ACAD/HON/SET/SET7.SET" "r"))
       (SETQ SETL7 (READ-LINE FC))
       (IF (OR (= SETL7 "") (= SETL7 NIL))
           (CLOSE FC)
       )
       (IF (OR (= SETL7 "") (= SETL7 NIL))
           (PROGN
              (PROMPT "\nPLEASE SETTING LAYER:" )
              (SETQ FC (OPEN "/ACAD/HON/SET/SET7.SET" "w"))
              (setq SETL7 (GETSTRING T"\nSETTING LAYER ? <7>:"))
              (IF (= SETL7 "")
                  (WRITE-LINE "7" FC)
                  (WRITE-LINE SETL7 FC)
              )
           (CLOSE FC)
           )
       )
       (SETQ FC (OPEN "/ACAD/HON/SET/SET7.SET" "r"))
       (SETQ SETL7 (READ-LINE FC))
       (CLOSE FC)
       (PROMPT "\nLAYER NAME IS:" )(PROMPT SETL7)(TERPRI)
    )
)

(SETQ ANS (strcase (GETSTRING "\nDO YOU WANT TO CHANGE LAST SETTING <Y/N> N:")))
(IF (= ANS "Y")
    (PROGN
       (PROMPT "\nPLEASE SETTING LAYER:" )
       (SETQ FC (OPEN "/ACAD/HON/SET/SET7.SET" "w"))
       (PROMPT "\nLAYER IS " )(PROMPT "<")(PROMPT SETL7) (PROMPT ">:")
       (SETQ SETW7 SETL7)
       (setq SETL7 (GETSTRING T))
       (IF (OR (= SETL7 "") (= SETL7 NIL))
               (WRITE-LINE SETW7 FC)
               (WRITE-LINE SETL7 FC)
       )
       (CLOSE FC)
       (SETQ FC (OPEN "/ACAD/HON/SET/SET7.SET" "r"))
       (SETQ SETL7 (READ-LINE FC))
       (CLOSE FC)
       (PROMPT "\nLAYER NOW IS:" )(PROMPT SETL7)(TERPRI)
  )
)

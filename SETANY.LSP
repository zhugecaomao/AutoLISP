(PRINC "\nSelect Layer To SET:")
;(IF (= (TYPE F1) 'FILE ) "YES"  (STOP))
;(IF (= (TYPE F2) 'FILE ) "YES" (STOP))
(setq LA1 (entget (car (entsel"\nSelect Layer To Set:\n"))))
(SETQ LAB (CDR LA1))
(SETQ LRB (ASSOC 8 LAB))
(SETQ LR (CDR LRB))
(SETVAR "CMDECHO" 0)
(IF LA1 (COMMAND "LAYER" "SET" LR "")
(SETVAR "CMDECHO" 1))

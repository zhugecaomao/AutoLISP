(DEFUN C:skt-3()
(COMMAND "SETVAR" "HIGHLIGHT" "1")
(SETQ D (GETREAL"\nInput skt dia:"))
(SETQ P1 (GETPOINT "\nInput insert Point:"))
(IF (= D 3)
    (PROGN
       (SETQ BD1 5)
       (SETQ BD2 6)
    )
)
(IF (= D 4)
    (PROGN
       (SETQ BD1 6.5)
       (SETQ BD2 7.5)
    )
)
(IF (= D 5)
    (PROGN
       (SETQ BD1 8)
       (SETQ BD2 9)
    )
)
(IF (= D 6)
    (PROGN
       (SETQ BD1 10)
       (SETQ BD2 11)
    )
)
(IF (= D 8)
    (PROGN
       (SETQ BD1 13)
       (SETQ BD2 14)
    )
)
(IF (= D 10)
    (PROGN
       (SETQ BD1 16)
       (SETQ BD2 17.5)
    )
)
(IF (= D 12)
    (PROGN
       (SETQ BD1 18)
       (SETQ BD2 20)
    )
)
(IF (= D 14)
    (PROGN
       (SETQ BD1 21)
       (SETQ BD2 23)
    )
)
(IF (= D 16)
    (PROGN
       (SETQ BD1 24)
       (SETQ BD2 26)
    )
)
(IF (= D 20)
    (PROGN
       (SETQ BD1 28)
       (SETQ BD2 30)
    )
)
(IF (= D 22)
    (PROGN
       (SETQ BD1 30)
       (SETQ BD2 32)
    )
)
(IF (= D 24)
    (PROGN
       (SETQ BD1 33)
       (SETQ BD2 35)
    )
)
(IF (= D 30)
    (PROGN
       (SETQ BD1 42)
       (SETQ BD2 45)
    )
)
(IF (= D 36)
    (PROGN
       (SETQ BD1 50)
       (SETQ BD2 54)
    )
)
(SETQ D1 D)
(SETQ D2 (+ (* P 0.6495) D))
(SETQ D3 (+ (* P 1.732) D))
(COMMAND "LAYER" "SET" "BLT1" "")
(COMMAND "CIRCLE" P1 D1)
(COMMAND "LAYER" "SET" "BLT3" "")
(COMMAND "CIRCLE" P1 D2)
(SETQ CP1 (LIST (CAR P1) (+ (CADR P1) D2 1)))
(SETQ CP2 (LIST (CAR P1) (- (CADR P1) D2 1)))
(SETQ CP3 (LIST (- (CAR P1) D2 1) (CADR P1)))
(SETQ CP4 (LIST (+ (CAR P1) D2 1) (CADR P1)))
(COMMAND "LAYER" "SET" "BLT2" "")
(COMMAND "LINE" CP1 CP2 "")
(COMMAND "LINE" CP3 CP4 "")
(COMMAND "SETVAR" "HIGHLIGHT" "1")
(COMMAND "LAYER" "SET" "0" "")
)

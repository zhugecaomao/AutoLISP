(DEFUN C:SLY()
(SETQ #M8 "TEXT")
(SETQ #N8 "TEXT")
(SETQ #O8 "TEXT")
(SETQ #P8 "TEXT")
(SETQ #Q8 "TEXT")
(SETQ #R8 "TEXT")
(SETQ #W4 "DIM2")
(SETQ #W5 "DIM2")
(SETQ #W6 "DIM2")
(SETQ #X5 "DIM3")
(SETQ #X6 "DIM3")
(SETQ #Y1 "DIM3")
(SETQ #Y1 "DIM3")
(SETQ #Y2 "DIM3")
(SETQ #Y3 "DIM3")
(SETQ #Y4 "DIM3")
(SETQ #Y5 "DIM3")
(SETQ #Y6 "DIM3")
)

(vmon)
defun c:SM4
;(IF (= (TYPE F1) 'FILE ) "YES"  (STOP))
;(IF (= (TYPE F2) 'FILE ) "YES" (STOP))
(SETQ BNAME (GETINT "\nInput basename:"))
(setq S (getreal "\nEnter [A] size:"))
(setq U (getreal "\nEnter [B] size:"))
(setq V (getreal "\nEnter [C] size:"))
(SETQ P1 (GETPOINT "\nInsert Point:"))
(SETQ W1 P1)
(SETQ BNAME (ITOA BNAME))
(SETQ B (SUBSTR  BNAME 1 2))
(SETQ E (SUBSTR  BNAME 3 2))
(SETQ B (STRCAT B "0"))
(SETQ E (STRCAT E "0"))
(SETQ B (ATOI B))
(SETQ E (ATOI E))
(SETQ BNAME (ATOI BNAME))
(IF (= BNAME 1518)
    (PROGN
     (setq A 200)
     (setq C 90)
     (setq D 28)
     (setq F 162)
     (setq G 72)
     (setq H 70)
     (setq I 26)
     (setq J 24)
     (setq K 48)
     (setq L 72)
     (setq M 114)
     (setq N 120)
     (setq O 52)
     (setq P 96)
     (setq gp 16)
     (setq SP 16)
     (setq rp 12)
     (setq mA 6)
     (setq mB 10)
     (setq Q  25 )
     (setq R  15 )
     (setq T  15 )
     (setq w  13 )
     (setq x  15 )
     (setq y  0 )
     (setq LA1 20)
   )
)
(IF (= BNAME 1520)
    (PROGN
     (setq A 200)
     (setq C 90)
     (setq D 28)
     (setq F 182)
     (setq G 82)
     (setq H 80)
     (setq I 36)
     (setq J 34)
     (setq K 48)
     (setq L 72)
     (setq M 114)
     (setq N 120)
     (setq O 72)
     (setq P 116)
     (setq SP 16)
     (setq gp 16)
     (setq rp 12)
     (setq mA 6)
     (setq mB 10)
     (setq Q 25)
     (setq R 15)
     (setq T 15)
     (setq w 13)
     (setq x 15)
     (setq Y 0)
     (setq LA1 20)
   )
)
(SETQ RR 1)
(IF (= BNAME 1523)
    (PROGN
     (setq A 200)
     (setq C 90)
     (setq D 28)
     (setq F 212)
     (setq G 97)
     (setq H 95)
     (setq I 51)
     (setq J 49)
     (setq K 48)
     (setq L 72)
     (setq M 114)
     (setq N 120)
     (setq O 102)
     (setq P 146)
     (setq SP 16)
     (setq gp 16)
     (setq rp 12)
     (setq mA 6)
     (setq mB 10)
     (setq Q 25)
     (setq R 15)
     (setq T  15 )
     (setq w  13 )
     (setq x  15 )
     (setq Y  0 )
     (setq LA1 20)
   )
)
(SETQ RR 2)
(IF (= BNAME 1525)
    (PROGN
     (setq A 200)
     (setq C 90)
     (setq D 28)
     (setq F 232)
     (setq G 107)
     (setq H 105)
     (setq I 61)
     (setq J 59)
     (setq K 48)
     (setq L 72)
     (setq M 114)
     (setq N 120)
     (setq O 122)
     (setq P 166)
     (setq SP 16)
     (setq gp 16)
     (setq rp 12)
     (setq mA 6)
     (setq mB 10)
     (setq Q 25)
     (setq R 15)
     (setq T  15 )
     (setq w  13 )
     (setq x  15 )
     (setq Y  0 )
     (setq LA1 20)
   )
)
(SETQ RR 3)
(IF (= BNAME 1530)
    (PROGN
     (setq A 200)
     (setq C 90)
     (setq D 28)
     (setq F 282)
     (setq G 132)
     (setq H 130)
     (setq I 86)
     (setq J 84)
     (setq K 48)
     (setq L 72)
     (setq M 114)
     (setq N 120)
     (setq O 172)
     (setq P 216)
     (setq SP 16)
     (setq gp 16)
     (setq rp 12)
     (setq mA 6)
     (setq mB 10)
     (setq Q 25)
     (setq R 15)
     (setq T 15)
     (setq w 13)
     (setq x 15)
     (setq Y  0)
     (setq LA1 20)
   )
)
(IF (= BNAME 1820)
    (PROGN
     (setq A 230)
     (setq C 110)
     (setq D 33)
     (setq F 180)
     (setq G 77)
     (setq H 75)
     (setq I 23)
     (setq J 21)
     (setq K 68)
     (setq L 90)
     (setq M 140)
     (setq N 145)
     (setq O 46)
     (setq P 98)
     (setq SP 20)
     (setq rp 12)
     (setq mA 8)
     (setq mB 12)
     (setq Q 30)
     (setq R 15)
     (setq T 15)
     (setq w 13)
     (setq x 15)
     (setq Y  0)
     (setq LA1 20)
   )
)
(IF (= BNAME 1823)
    (PROGN
     (setq A 230)
     (setq C 110)
     (setq D 33)
     (setq F 210)
     (setq G 92)
     (setq H 90)
     (setq I 38)
     (setq J 36)
     (setq K 68)
     (setq L 90)
     (setq M 140)
     (setq N 145)
     (setq O 76)
     (setq P 128)
     (setq SP 20)
     (setq gp 20)
     (setq rp 12)
     (setq mA 8)
     (setq mB 12)
     (setq Q 30)
     (setq R 15)
     (setq T 15)
     (setq w 13)
     (setq x 15)
     (setq Y  0)
     (setq LA1 20)
   )
)
(SETQ RR 7)
(IF (= BNAME 1825)
    (PROGN
     (setq A 230)
     (setq C 110)
     (setq D 33)
     (setq F 230)
     (setq G 102)
     (setq H 100)
     (setq I 48)
     (setq J 46)
     (setq K 68)
     (setq L 90)
     (setq M 140)
     (setq N 145)
     (setq O 96)
     (setq P 148)
     (setq SP 20)
     (setq gp 20)
     (setq rp 12)
     (setq mA 8)
     (setq mB 12)
     (setq Q 30)
     (setq R 15)
     (setq T 15)
     (setq w 13)
     (setq x 15)
     (setq Y  0)
     (setq LA1 20)
   )
)
(SETQ RR 8)
(IF (= BNAME 2020)
    (PROGN
     (setq A 250)
     (setq C 120)
     (setq D 38)
     (setq F 180)
     (setq G 77)
     (setq H 75)
     (setq I 23)
     (setq J 21)
     (setq K 84)
     (setq L 100)
     (setq M 154)
     (setq N 160)
     (setq O 46)
     (setq P 98)
     (setq SP 20)
     (setq gp 20)
     (setq rp 12)
     (setq mA 8)
     (setq mB 12)
     (setq Q 30)
     (setq R 20)
     (setq T 20)
     (setq w 13)
     (setq x 15)
     (setq Y  0)
     (setq LA1 25)
   )
)
(SETQ RR 9)
(IF (= BNAME 2023)
    (PROGN
     (setq A 250)
     (setq C 120)
     (setq D 38)
     (setq F 210)
     (setq G 92)
     (setq H 90)
     (setq I 38)
     (setq J 36)
     (setq K 80)
     (setq L 100)
     (setq M 154)
     (setq N 160)
     (setq O 76)
     (setq P 128)
     (setq SP 20)
     (setq gp 20)
     (setq rp 15)
     (setq mA 8)
     (setq mB 12)
     (setq Q 30)
     (setq R 20)
     (setq T 20)
     (setq w 15)
     (setq x 20)
     (setq Y  0)
     (setq LA1 25)
   )
)
(SETQ RR 10)
(IF (= BNAME 2025)
    (PROGN
     (setq A 250)
     (setq C 120)
     (setq D 38)
     (setq F 230)
     (setq G 102)
     (setq H 100)
     (setq I 48)
     (setq J 46)
     (setq K 80)
     (setq L 100)
     (setq M 154)
     (setq N 160)
     (setq O 96)
     (setq O 148)
     (setq SP 20)
     (setq gp 20)
     (setq rp 15)
     (setq mA 8)
     (setq mB 12)
     (setq Q 30)
     (setq R 20)
     (setq T 20)
     (setq w 15)
     (setq x 20)
     (setq Y  0)
     (setq LA1 25)
   )
)
(SETQ RR 11)
(IF (= BNAME 2030)
    (PROGN
     (setq A 250)
     (setq C 120)
     (setq D 38)
     (setq F 280)
     (setq G 127)
     (setq H 125)
     (setq I 73)
     (SETQ J 71)
     (setq K 80)
     (setq L 100)
     (setq M 154)
     (setq N 160)
     (setq O 146)
     (setq P 198)
     (setq SP 20)
     (setq gp 20)
     (setq rp 15)
     (setq mA 8)
     (setq mB 12)
     (setq Q 30)
     (setq R 20)
     (setq T 20)
     (setq w 15)
     (setq x 20)
     (setq Y  0)
     (setq LA1 25)
   )
)
(IF (= BNAME 2035)
    (PROGN
     (setq A 250)
     (setq C 120)
     (setq D 38)
     (setq F 330)
     (setq G 152)
     (setq H 150)
     (setq I 98)
     (setq J 96)
     (setq K 80)
     (setq L 100)
     (setq M 154)
     (setq N 160)
     (setq O 196)
     (setq P 248)
     (setq SP 20)
     (setq gp 20)
     (setq rp 15)
     (setq mA 8)
     (setq mB 12)
     (setq Q 30)
     (setq R 20)
     (setq T 20)
     (setq w 15)
     (setq x 20)
     (setq Y  0)
     (setq LA1 25)
   )
)
(IF (= BNAME 2323)
    (PROGN
     (setq A 280)
     (setq C 140)
     (setq D 43)
     (setq F 210)
     (setq G 92)
     (setq H 90)
     (setq I 37)
     (setq J 35)
     (setq K 106)
     (setq L 120)
     (setq M 184)
     (setq N 185)
     (setq O 74)
     (setq P 128)
     (setq SP 20)
     (setq gp 20)
     (setq rp 15)
     (setq mA 8)
     (setq mB 12)
     (setq Q 30)
     (setq R 20)
     (setq T 20)
     (setq w 15)
     (setq x 20)
     (setq Y  0)
     (setq LA1 25)
   )
)
(SETQ RR 12)
(IF (= BNAME 2325)
    (PROGN
     (setq A 280)
     (setq C 140)
     (setq D 43)
     (setq F 230)
     (setq G 102)
     (setq H 100)
     (setq I 47)
     (setq J 45)
     (setq K 106)
     (setq L 120)
     (setq M 184)
     (setq N 185)
     (setq O 94)
     (setq P 148)
     (setq SP 20)
     (setq gp 20)
     (setq rp 15)
     (setq mA 8)
     (setq mB 12)
     (setq Q 30)
     (setq R 20)
     (setq T 20)
     (setq w 15)
     (setq x 20)
     (setq Y  0)
     (setq LA1 25)
   )
)
(IF (= BNAME 2327)
    (PROGN
     (setq A 280)
     (setq C 140)
     (setq D 43)
     (setq F 250)
     (setq G 112)
     (setq H 110)
     (setq I 56)
     (setq J 54)
     (setq K 106)
     (setq L 120)
     (setq M 184)
     (setq N 185)
     (setq O 112)
     (setq P 166)
     (setq SP 20)
     (setq gp 20)
     (setq rp 15)
     (setq mA 8)
     (setq mB 14)
     (setq Q 30)
     (setq R 20)
     (setq T 20)
     (setq w 15)
     (setq x 20)
     (setq Y  0)
     (setq LA1 25)
   )
)
(IF (= BNAME 2330)
    (PROGN
     (setq A 280)
     (setq C 140)
     (setq D 43)
     (setq F 280)
     (setq G 127)
     (setq H 125)
     (setq I 106)
     (setq J 120)
     (setq K 184)
     (setq L 185)
     (setq M 174)
     (SETQ SP 20)
     (setq gp 20)
     (setq rp 15)
     (setq mA 8)
     (setq mB 14)
     (setq Q 30)
     (setq R 20)
     (setq T 20)
     (setq w 15)
     (setq x 20)
     (setq Y  0)
     (setq LA1 25)
   )
)
(IF (= BNAME 2525)
    (PROGN
     (setq A 300)
     (setq C 150)
     (setq D 48)
     (setq F 230)
     (setq G 97)
     (setq H 95)
     (setq I 33)
     (setq J 35)
     (setq K 110)
     (setq L 130)
     (setq M 194)
     (setq N 200)
     (setq O 70)
     (setq P 130)
     (SETQ SP 25)
     (setq gp 25)
     (setq rp 15)
     (setq mA 8)
     (setq mB 14)
     (setq Q 35)
     (setq R 25)
     (setq T 25)
     (setq w 15)
     (setq x 20)
     (setq Y  0)
     (setq LA1 25)
   )
)
(IF (= BNAME 2527)
    (PROGN
     (setq A 300)
     (setq C 150)
     (setq D 48)
     (setq F 250)
     (setq G 107)
     (setq H 105)
     (setq I 45)
     (setq J 43)
     (SETQ K 110)
     (setq L 130)
     (setq M 194)
     (setq N 200)
     (setq O 90)
     (setq P 150)
     (setq SP 25)
     (setq gp 25)
     (setq rp 15)
     (setq mA 8)
     (setq mB 14)
     (setq Q 35)
     (setq R 25)
     (setq T 25)
     (setq w 15)
     (setq x 20)
     (setq Y  0)
     (setq LA1 25)
   )
)
(SETQ RR 14)
(IF (= BNAME 2530)
    (PROGN
     (setq A 300)
     (setq C 150)
     (setq D 48)
     (setq F 280)
     (setq G 122)
     (setq H 120)
     (setq I 60)
     (setq J 58)
     (setq K 110)
     (setq L 130)
     (setq M 194)
     (setq N 200)
     (setq O 120)
     (setq P 180)
     (setq SP 25)
     (setq gp 25)
     (setq rp 15)
     (setq mA 8)
     (setq mB 14)
     (setq Q 35)
     (setq R 25)
     (setq T 25)
     (setq w 15)
     (setq x 20)
     (setq Y  0)
     (setq LA1 25)
   )
)
(IF (= BNAME 2535)
    (PROGN
     (setq A 300)
     (setq C 150)
     (setq D 48)
     (setq F 330)
     (setq G 147)
     (setq H 145)
     (setq I 85)
     (setq J 83)
     (setq K 102)
     (setq L 130)
     (setq M 194)
     (setq N 200)
     (setq O 170)
     (setq P 230)
     (setq SP 25)
     (setq gp 25)
     (setq rp 20)
     (setq mA 8)
     (setq mB 14)
     (setq Q 30)
     (setq R 20)
     (setq T 25)
     (setq w 15)
     (setq x 20)
     (setq Y  0)
     (setq LA1 25)
   )
)
(IF (= BNAME 2540)
    (PROGN
     (setq A 300)
     (setq C 150)
     (setq D 48)
     (setq F 380)
     (setq G 172)
     (setq H 170)
     (setq I 110)
     (setq J 108)
     (setq K 102)
     (setq L 130)
     (setq M 194)
     (setq N 200)
     (setq O 220)
     (setq P 280)
     (setq SP 25)
     (setq gp 25)
     (setq rp 20)
     (setq mA 8)
     (setq mB 14)
     (setq Q 30)
     (setq R 20)
     (setq T 25)
     (setq w 15)
     (setq x 20)
     (setq Y  0)
     (setq LA1 25)
   )
)
(SETQ RR 15)
(IF (= BNAME 2730)
    (PROGN
     (setq A 320)
     (setq C 160)
     (setq D 53)
     (setq F 276)
     (setq G 122)
     (setq H 120)
     (setq I 60)
     (setq J 58)
     (setq K 114)
     (setq L 136)
     (setq M 214)
     (setq N 215)
     (setq O 120)
     (setq P 180)
     (setq SP 25)
     (setq gp 25)
     (setq rp 20)
     (setq mA 10)
     (setq mB 14)
     (setq Q 35)
     (setq R 25)
     (setq T 25)
     (setq w 15)
     (setq x 20)
     (setq Y  0)
     (setq LA1 25)
   )
)
(IF (= BNAME 2735)
    (PROGN
     (setq A 320)
     (setq C 160)
     (setq D 53)
     (setq F 326)
     (setq G 147)
     (setq H 145)
     (setq I 85)
     (setq J 83)
     (setq K 114)
     (setq L 136)
     (setq M 214)
     (setq N 215)
     (setq O 170)
     (setq P 230)
     (setq SP 25)
     (setq gp 25)
     (setq rp 20)
     (setq mA 10)
     (setq mB 14)
     (setq Q 35)
     (setq R 25)
     (setq T 25)
     (setq w 15)
     (setq x 20)
     (setq Y  0)
     (setq LA1 25)
   )
)
(IF (= BNAME 3030)
    (PROGN
     (setq A 350)
     (setq C 180)
     (setq D 58)
     (setq F 276)
     (setq G 117)
     (setq H 115)
     (setq I 49)
     (setq J 47)
     (setq K 134)
     (setq L 156)
     (setq M 234)
     (setq N 240)
     (setq O 98)
     (setq P 164)
     (setq SP 30)
     (setq gp 30)
     (setq rp 20)
     (setq mA 10)
     (setq mB 14)
     (setq Q 45)
     (setq R 30)
     (setq T 30)
     (setq w 20)
     (setq x 25)
     (setq Y  0)
     (setq LA1 25)
   )
)
(IF (= BNAME 3035)
    (PROGN
     (setq A 350)
     (setq C 180)
     (setq D 58)
     (setq F 326)
     (setq G 142)
     (setq H 140)
     (setq I 74)
     (setq J 72)
     (setq K 134)
     (setq L 156)
     (setq M 234)
     (setq N 240)
     (setq O 148)
     (setq P 214)
     (setq SP 30)
     (setq gp 30)
     (setq rp 20)
     (setq mA 10)
     (setq mB 14)
     (setq Q 45)
     (setq R 30)
     (setq T 30)
     (setq w 20)
     (setq x 25)
     (setq Y  0)
     (setq LA1 25)
   )
)
(SETQ RR 16)
 (IF (= BNAME 3040)
  (PROGN
      (setq A 350)
      (setq C 180)
      (setq D 58)
      (setq F 376)
      (setq G 167)
      (setq H 165)
      (setq I 99)
      (setq J 97)
      (setq K 134)
      (setq L 156)
      (setq M 234)
      (setq N 240)
      (setq O 198)
      (setq P 264)
      (setq SP 30)
      (setq gp 30)
      (setq rp 20)
      (setq mA 10)
      (setq mB 14)
      (setq Q 45)
      (setq R 30)
     (setq T 30)
      (setq w 20)
      (setq x 25)
      (setq Y  0)
      (setq LA1 30)
    )
 )
(IF (= BNAME 3045)
    (PROGN
     (setq A 350)
     (setq C 180)
     (setq D 58)
     (setq F 426)
     (setq G 192)
     (setq H 190)
     (setq I 122)
     (setq J 120)
     (setq K 128)
     (setq L 156)
     (setq M 234)
     (setq N 240)
     (setq O 244)
     (setq P 312)
     (setq SP 30)
     (setq gp 30)
     (setq rp 25)
     (setq mA 10)
     (setq mB 16)
     (setq Q 45)
     (setq R 30)
     (setq T 30)
     (setq w 20)
     (setq x 25)
     (setq Y  0)
     (setq LA1 30)
   )
)
(IF (= BNAME 3050)
    (PROGN
     (setq A 350)
     (setq C 180)
     (setq D 58)
     (setq F 476)
     (setq G 217)
     (setq H 215)
     (setq I 147)
     (setq J 145)
     (setq K 128)
     (setq L 156)
     (setq M 234)
     (setq N 240)
     (setq O 294)
     (setq P 362)
     (setq SP 30)
     (setq gp 30)
     (setq rp 25)
     (setq mA 10)
     (setq mB 16)
     (setq Q 45)
     (setq R 30)
     (setq T 30)
     (setq w 20)
     (setq x 25)
     (setq Y  0)
     (setq LA1 30)
   )
)
(IF (= BNAME 3060)
    (PROGN
     (setq A 350)
     (setq C 180)
     (setq D 58)
     (setq F 576)
     (setq G 267)
     (setq H 265)
     (setq I 197)
     (setq J 195)
     (setq K 128)
     (setq L 156)
     (setq M 234)
     (setq N 240)
     (setq O 394)
     (setq P 462)
     (setq SP 30)
     (setq gp 30)
     (setq rp 20)
     (setq mA 10)
     (setq mB 16)
     (setq Q 45)
     (setq R 30)
     (setq T 30)
     (setq w 20)
     (setq x 25)
     (setq Y  0)
     (setq LA1 30)
   )
)
(SETQ RR 17)
(IF (= BNAME 3335)
    (PROGN
     (setq A 400)
     (setq C 210)
     (setq D 58)
     (setq F 326)
     (setq G 142)
     (setq H 140)
     (setq I 74)
     (setq J 72)
     (setq K 154)
     (setq L 186)
     (setq M 264)
     (setq N 270)
     (setq O 148)
     (setq P 214)
     (setq SP 30)
     (setq gp 30)
     (setq rp 25)
     (setq mA 10)
     (setq mB 14)
     (setq Q 45)
     (setq R 30)
     (setq T 35)
     (setq w 20)
     (setq x 25)
     (setq Y  0)
     (setq LA1 30)
   )
)
(IF (= BNAME 3340)
    (PROGN
     (setq A 400)
     (setq C 210)
     (setq D 58)
     (setq F 376)
     (setq G 167)
     (setq H 165)
     (setq I 99)
     (setq J 97)
     (setq K 154)
     (setq L 186)
     (setq M 264)
     (setq N 270)
     (setq O 198)
     (setq P 264)
     (setq SP 30)
     (setq gp 30)
     (setq rp 25)
     (setq mA 10)
     (setq mB 14)
     (setq Q 45)
     (setq R 30)
     (setq T 30)
     (setq w 20)
     (setq x 25)
     (setq Y  0)
     (setq LA1 30)
   )
)
(SETQ RR 18)
(IF (= BNAME 3535)
    (PROGN
     (setq A 400)
     (setq C 220)
     (setq D 63)
     (setq F 326)
     (setq G 142)
     (setq H 140)
     (setq I 72)
     (setq J 70)
     (setq K 164)
     (setq L 196)
     (setq M 284)
     (setq N 285)
     (setq O 144)
     (setq P 212)
     (setq SP 30)
     (setq gp 30)
     (setq rp 25)
     (setq mA 10)
     (setq mB 16)
     (setq Q 45)
     (setq R 35)
     (setq T 35)
     (setq w 20)
     (setq x 25)
     (setq Y  0)
     (setq LA1 30)
   )
)
(IF (= BNAME 3540)
    (PROGN
     (setq A 400)
     (setq C 220)
     (setq D 63)
     (setq F 376)
     (setq G 167)
     (setq H 165)
     (setq I 97)
     (setq J 95)
     (setq K 164)
     (setq L 196)
     (setq M 284)
     (setq N 285)
     (setq O 194)
     (setq P 262)
     (setq SP 30)
     (setq gp 30)
     (setq rp 25)
     (setq mA 10)
     (setq mB 16)
     (setq Q 45)
     (setq R 35)
     (setq T 35)
     (setq w 20)
     (setq x 25)
     (setq Y  0)
     (setq LA1 30)
   )
)
(IF (= BNAME 3545)
    (PROGN
     (setq A 400)
     (setq C 220)
     (setq D 63)
     (setq F 426)
     (setq G 192)
     (setq H 190)
     (setq I 122)
     (setq J 120)
     (setq K 164)
     (setq L 196)
     (setq M 284)
     (setq N 285)
     (setq O 244)
     (setq P 312)
     (setq SP 30)
     (setq gp 30)
     (setq rp 25)
     (setq mA 10)
     (setq mB 16)
     (setq Q 45)
     (setq R 35)
     (setq T 35)
     (setq w 20)
     (setq x 25)
     (setq Y  0)
     (setq LA1 30)
   )
)
(IF (= BNAME 3550)
    (PROGN
     (setq A 400)
     (setq C 220)
     (setq D 63)
     (setq F 476)
     (setq G 212)
     (setq H 210)
     (setq I 134)
     (setq J 132)
     (setq K 152)
     (setq L 196)
     (setq M 274)
     (setq N 285)
     (setq O 268)
     (setq P 344)
     (setq SP 35)
     (setq gp 35)
     (setq rp 25)
     (setq mA 10)
     (setq mB 16)
     (setq Q 50)
     (setq R 35)
     (setq T 35)
     (setq w 20)
     (setq x 25)
     (setq Y  0)
     (setq LA1 30)
   )
)
(IF (= BNAME 3560)
    (PROGN
     (setq A 400)
     (setq C 220)
     (setq D 63)
     (setq F 576)
     (setq G 262)
     (setq H 260)
     (setq I 184)
     (setq J 182)
     (setq K 152)
     (setq L 196)
     (setq M 274)
     (setq N 285)
     (setq O 368)
     (setq P 444)
     (setq SP 35)
     (setq gp 35)
     (setq rp 25)
     (setq mA 10)
     (setq mB 16)
     (setq Q 50)
     (setq R 35)
     (setq T 35)
     (setq w 20)
     (setq x 25)
     (setq Y  0)
     (setq LA1 30)
   )
)
(IF (= BNAME 4040)
    (PROGN
     (setq A 450)
     (setq C 260)
     (setq D 68)
     (setq F 374)
     (setq G 162)
     (setq H 160)
     (setq I 84)
     (setq J 82)
     (setq K 198)
     (setq L 234)
     (setq M 324)
     (setq N 330)
     (setq O 168)
     (setq P 244)
     (setq SP 35)
     (setq gp 35)
     (setq rp 25)
     (setq mA 12)
     (setq mB 16)
     (setq Q 50)
     (setq R 35)
     (setq T 35)
     (setq w 25)
     (setq x 30)
     (setq Y  0)
     (setq LA1 30)
   )
)
(IF (= BNAME 4045)
    (PROGN
     (setq A 450)
     (setq C 260)
     (setq D 68)
     (setq F 424)
     (setq G 187)
     (setq H 185)
     (setq I 109)
     (setq J 107)
     (setq K 198)
     (setq L 234)
     (setq M 324)
     (setq N 330)
     (setq O 218)
     (setq P 294)
     (setq SP 35)
     (setq gp 35)
     (setq rp 25)
     (setq mA 12)
     (setq mB 16)
     (setq Q 50)
     (setq R 35)
     (setq T 35)
     (setq w 25)
     (setq x 30)
     (setq Y  0)
     (setq LA1 35)
   )
)
(IF (= BNAME 4050)
    (PROGN
     (setq A 450)
     (setq C 260)
     (setq D 68)
     (setq F 474)
     (setq G 212)
     (setq H 210)
     (setq I 134)
     (setq J 132)
     (setq K 198)
     (setq L 234)
     (setq M 324)
     (setq N 330)
     (setq O 268)
     (setq P 344)
     (setq SP 35)
     (setq gp 35)
     (setq rp 25)
     (setq mA 12)
     (setq mB 16)
     (setq Q 50)
     (setq R 35)
     (setq T 35)
     (setq w 25)
     (setq x 30)
     (setq Y  0)
     (setq LA1 35)
   )
)
(IF (= BNAME 4060)
    (PROGN
     (setq A 450)
     (setq C 260)
     (setq D 68)
     (setq F 574)
     (setq G 262)
     (setq H 260)
     (setq I 184)
     (setq J 182)
     (setq K 198)
     (setq L 234)
     (setq M 324)
     (setq N 330)
     (setq O 368)
     (setq P 444)
     (setq SP 35)
     (setq gp 35)
     (setq rp 25)
     (setq mA 12)
     (setq mB 16)
     (setq Q 50)
     (setq R 35)
     (setq T 35)
     (setq w 25)
     (setq x 30)
     (setq Y  0)
     (setq LA1 35)
   )
)
(IF (= BNAME 4070)
    (PROGN
     (setq A 450)
     (setq C 260)
     (setq D 68)
     (setq F 674)
     (setq G 312)
     (setq H 310)
     (setq I 234)
     (setq J 232)
     (setq K 198)
     (setq L 234)
     (setq M 324)
     (setq N 330)
     (setq O 468)
     (setq P 544)
     (setq SP 35)
     (setq gp 35)
     (setq rp 25)
     (setq mA 12)
     (setq mB 16)
     (setq Q 50)
     (setq R 35)
     (setq T 35)
     (setq w 25)
     (setq x 30)
     (setq Y  0)
     (setq LA1 35)
   )
)
(IF (= BNAME 4545)
    (PROGN
     (setq A 550)
     (setq C 290)
     (setq D 78)
     (setq F 424)
     (setq G 182)
     (setq H 180)
     (setq I 97)
     (setq J 95)
     (setq K 226)
     (setq L 264)
     (setq M 364)
     (setq N 370)
     (setq O 194)
     (setq P 276)
     (setq SP 40)
     (setq gp 40)
     (setq rp 30)
     (setq mA 12)
     (setq mB 16)
     (setq Q 60)
     (setq R 40)
     (setq T 40)
     (setq w 25)
     (setq x 30)
     (setq Y  0)
     (setq LA1 35)
   )
)
(IF (= BNAME 4550)
    (PROGN
     (setq A 550)
     (setq C 450)
     (setq D 290)
     (setq F 474)
     (setq G 207)
     (setq H 205)
     (setq I 122)
     (setq J 120)
     (setq K 226)
     (setq L 264)
     (setq M 364)
     (setq N 370)
     (setq O 244)
     (setq P 326)
     (setq SP 40)
     (setq gp 40)
     (setq rp 30)
     (setq mA 12)
     (setq mB 16)
     (setq Q 60)
     (setq R 40)
     (setq T 40)
     (setq w 25)
     (setq x 30)
     (setq Y  0)
     (setq LA1 35)
   )
)
(IF (= BNAME 5050)
    (PROGN
     (setq A 600)
     (setq C 320)
     (setq D 88)
     (setq F 474)
     (setq G 207)
     (setq H 205)
     (setq I 122)
     (setq J 120)
     (setq K 256)
     (setq L 294)
     (setq M 410)
     (setq N 414)
     (setq O 244)
     (setq P 326)
     (setq SP 40)
     (setq gp 40)
     (setq rp 30)
     (setq mA 12)
     (setq mB 16)
     (setq Q 60)
     (setq R 40)
     (setq T 40)
     (setq w 25)
     (setq x 30)
     (setq Y  0)
     (setq LA1 35)
   )
)
(IF (= BNAME 5060)
    (PROGN
     (setq A 600)
     (setq C 320)
     (setq D 88)
     (setq F 574)
     (setq G 257)
     (setq H 255)
     (setq I 172)
     (setq J 170)
     (setq K 256)
     (setq L 294)
     (setq M 410)
     (setq N 414)
     (setq O 344)
     (setq P 426)
     (setq SP 40)
     (setq gp 40)
     (setq rp 30)
     (setq mA 12)
     (setq mB 16)
     (setq Q 60)
     (setq R 40)
     (setq T 40)
     (setq w 25)
     (setq x 30)
     (setq Y  0)
     (setq LA1 35)
   )
)
(IF (= BNAME 5070)
    (PROGN
     (setq A 600)
     (setq C 320)
     (setq D 88)
     (setq F 674)
     (setq G 307)
     (setq H 305)
     (setq I 222)
     (setq J 220)
     (setq K 256)
     (setq L 294)
     (setq M 410)
     (setq N 414)
     (setq O 444)
     (setq P 526)
     (setq SP 40)
     (setq gp 40)
     (setq rp 30)
     (setq mA 12)
     (setq mB 16)
     (setq Q 60)
     (setq R 40)
     (setq T 40)
     (setq w 25)
     (setq x 30)
     (setq Y  0)
     (setq LA1 35)
   )
)

(SETQ P2 (LIST (+ (CAR P1) A)(CADR P1)))
(SETQ P3 (LIST (CAR P2 ) (- (CADR P2) E)))
(SETQ P4 (LIST (- (CAR P3) A) (CADR P3)))
(SETQ P5 (LIST (/ (+ (CAR P1) (CAR P2)) 2) (+ (CADR P1) 10))) ;CENTER LINE UP
(SETQ P6 (LIST (/ (+ (CAR P3) (CAR P4)) 2) (- (CADR P4) 10)));CENTER LINE DOWN
(SETQ P7 (LIST (- (/ (+ (CAR P1) (CAR P4)) 2) 10) (/ (+ (CADR P1) (CADR P4)) 2)));CENTER LINE LEGT
(SETQ P8 (LIST (+ (/ (+ (CAR P2) (CAR P3)) 2) 10) (/ (+ (CADR P2) (CADR P3)) 2)));RIGHT
(COMMAND "LAYER" "S" "DRAW" "")
(COMMAND "LINE" P1 P2 P3 P4 "C")   ;draw outside box
(COMMAND "LAYER" "S"  "center" "")
(COMMAND "LINE" P5 P6 "" "LINE" P7 P8 "") ;DRAW CENETR
(COMMAND "LAYER" "S"  "HIDDEN" "")
(COMMAND "LINE" (LIST (+ (CAR P5) (/ C 2))  (- (CADR P5) 10))
                (LIST (+ (CAR P6) (/ C 2))  (+ (CADR P6) 10)) "")
(COMMAND "LINE" (LIST (- (CAR P5) (/ C 2))  (- (CADR P5) 10))
                (LIST (- (CAR P6) (/ C 2))  (+ (CADR P6) 10)) "")
(COMMAND "LINE" (LIST (+ (CAR P5) (/ C 2) 2)  (- (CADR P5) 10))
                (LIST (+ (CAR P6) (/ C 2) 2)  (+ (CADR P6) 10)) "")
(COMMAND "LINE" (LIST (- (CAR P5) (/ C 2) 2)  (- (CADR P5) 10))
                (LIST (- (CAR P6) (/ C 2) 2)  (+ (CADR P6) 10)) "")
(SETQ SD (/ (- B C (* D 2)) 2))

(COMMAND "LINE" (LIST (+ (CAR P5) (/ C 2))  (- (CADR P5) 10))
                (LIST (+ (CAR P6) (/ C 2))  (+ (CADR P6) 10)) "")
(COMMAND "LINE" (LIST (- (CAR P5) (/ C 2))  (- (CADR P5) 10))
                (LIST (- (CAR P6) (/ C 2))  (+ (CADR P6) 10)) "")

(COMMAND "LAYER" "S"  "DRAW" "")
(COMMAND "LINE" (LIST (+ (CAR P5) (/ B 2))  (- (CADR P5) 10))
                (LIST (+ (CAR P6) (/ B 2))  (+ (CADR P6) 10)) "")
(COMMAND "LINE" (LIST (- (CAR P5) (/ B 2))  (- (CADR P5) 10))
                (LIST (- (CAR P6) (/ B 2))  (+ (CADR P6) 10)) "")

(SETQ D1 (/ (- A B) 2))
(SETQ D2 (+ (/ (- A B) 2 ) D))
(SETQ D3 (+ (/ (- A B) 2 ) D (/ (- B C  D D ) 2)))

(SETQ C4 (LIST (+ (CAR P6) (/ M 2)) (-(CADR P8) H))) ;G.P
(SETQ C3 (LIST (- (CAR P6) (/ M 2)) (-(CADR P8) G)))
(SETQ C2 (LIST (+ (CAR P5) (/ M 2)) (+(CADR P8) G)))
(SETQ C1 (LIST (- (CAR P5) (/ M 2)) (+(CADR P8) G)))

;      P1   P5   P2
;      +-----|-----+
;      |     |     |
;  P7-+------+-----+- P8
;      |     |     |
;      +-----|-----+
;      P4   P6   P3
(SETQ M4 (LIST (+ (CAR P6) (/ L 2)) (- (CADR P8) (/ f 2) ))) ;m6  center
(SETQ M3 (LIST (- (CAR P6) (/ L 2)) (- (CADR P7) (/ f 2) )))
(SETQ M2 (LIST (+ (CAR P5) (/ L 2)) (+ (CADR P8) (/ f 2) )))
(SETQ M1 (LIST (- (CAR P5) (/ L 2)) (+ (CADR P8) (/ f 2) )))

(SETQ Y4 (LIST (+ (CAR P6) (/ N 2)) (- (CADR P8) (/ P 2) ))) ;m10 center
(SETQ Y3 (LIST (- (CAR P6) (/ N 2)) (- (CADR P7) (/ P 2) )))
(SETQ Y2 (LIST (+ (CAR P5) (/ N 2)) (+ (CADR P8) (/ P 2) )))
(SETQ Y1 (LIST (- (CAR P5) (/ N 2)) (+ (CADR P8) (/ P 2) )))

(SETQ R4 (LIST (+ (CAR P6) (/ K 2)) (- (CADR P8) G)))        ;r.p center
(SETQ R3 (LIST (- (CAR P6) (/ K 2)) (- (CADR P8) G)))
(SETQ R2 (LIST (+ (CAR P5) (/ K 2)) (+ (CADR P8) G)))
(SETQ R1 (LIST (- (CAR P5) (/ K 2)) (+ (CADR P8) G)))

(SETQ sp4 (LIST (+ (CAR P6) (/ M 2)) (-(CADR P8) J)))         ;s.P center
(SETQ sp3 (LIST (- (CAR P6) (/ M 2)) (-(CADR P8) I)))
(SETQ sp2 (LIST (+ (CAR P5) (/ M 2)) (+(CADR P8) I)))
(SETQ sp1 (LIST (- (CAR P5) (/ M 2)) (+(CADR P8) I)))

(SETQ GP (ITOA GP))
(SETQ GP-1 (STRCAT "C:\\acad\hon\\G\\G" GP "-1"))
(command "insert" GP-1 C4 1 1 0)
(command "insert" GP-1 C3 1 1 0)
(command "insert" GP-1 C2 1 1 0)
(command "insert" GP-1 C1 1 1 0)

(SETQ SP (ITOA SP))
(SETQ SP-1 (STRCAT "C:\\acad\hon\\G\\SP" SP "-1"))
(command "insert" SP-1 SP4 1 1 0)
(command "insert" SP-1 SP3 1 1 0)
(command "insert" SP-1 SP2 1 1 0)
(command "insert" SP-1 SP1 1 1 0)

(SETQ RP (ITOA RP))
(SETQ RP-1 (STRCAT "C:\\acad\hon\\R\\R" RP "-1"))
(command "insert" RP-1 R4 1 1 0)
(command "insert" RP-1 R3 1 1 0)
(command "insert" RP-1 R2 1 1 0)
(command "insert" RP-1 R1 1 1 0)

(SETQ MA (ITOA MA))
(SETQ MA-1 (STRCAT "C:\\acad\hon\\B\\BLT1-" MA))
(command "insert" MA-1 M4 1 1 0)
(command "insert" MA-1 M3 1 1 0)
(command "insert" MA-1 M2 1 1 0)
(command "insert" MA-1 M1 1 1 0)

(SETQ MB (ITOA MB))
(SETQ MB-1 (STRCAT "C:\\acad\hon\\B\\BLT1-" MB))
(command "insert" MB-1 Y4 1 1 0)
(command "insert" MB-1 Y3 1 1 0)
(command "insert" MB-1 Y2 1 1 0)
(command "insert" MB-1 Y1 1 1 0)

(SETQ GP (ATOI GP))
(SETQ SP (ATOI SP))
(SETQ RP (ATOI RP))
(SETQ MA (ATOI MA))
(SETQ MB (ATOI MB))

(COMMAND "LAYER" "S" "DRAW" "")

(SETQ T1 A1)
; 2ST PICTURE
;DRAW BOX
(SETQ P1 (LIST (CAR P1) (- (CADR P1) E 100)))  ;SECOND ORG P1
(SETQ Z1 P1)
(SETQ W2 P1)
(COMMAND "LINE" P1 (LIST (+ A (CAR P1)) (CADR P1)) (LIST (+ A (CAR P1)) ;1ST BOX  Q
(- (CADR P1) Q)) (LIST (CAR P1 ) (- (CADR P1) Q )) P1 "")
;
(SETQ P1 (LIST (+ (CAR P1) (/ (- A B ) 2) ) (- (CADR P1 ) Q))) ;2ND BO3  R
(COMMAND "LINE" (LIST (+ B (CAR P1)) (CADR P1))
(LIST (+ B (CAR P1)) (- (CADR P1 ) R))
(LIST (CAR P1) (- (CADR P1) R)) P1 "")
;
(SETQ P1 (LIST (CAR P1) (- (CADR P1 ) R)))                   ;3ND BO3  S
(COMMAND "LINE" (LIST (+ B (CAR P1)) (CADR P1))
(LIST (+ B (CAR P1)) (- (CADR P1 ) S))
(LIST (CAR P1) (- (CADR P1) S)) P1 "")

(SETQ P1 (LIST (CAR P1) (- (CADR P1 ) S) ))                   ;4ND BOX  T
(COMMAND "LINE" (LIST (+ B (CAR P1)) (CADR P1))
(LIST (+ B (CAR P1)) (- (CADR P1 ) T))
(LIST (CAR P1) (- (CADR P1) T)) P1 "")
;                                                              ;5ND BOX  U
 (SETQ P1 (LIST (CAR P1) (- (CADR P1 ) T) ))
 (COMMAND "LINE" (LIST (+ B (CAR P1)) (CADR P1))
 (LIST (+ B (CAR P1)) (- (CADR P1 ) U)) "")
 (COMMAND "LINE" (LIST (CAR P1) (- (CADR P1) U)) P1 "")

 (SETQ P1 (LIST (CAR P1) (- (CADR P1 ) U) ))         ;OUTSIDE BOX
 (COMMAND "LINE" P1 (LIST (+ B (CAR P1)) (CADR P1))
 (LIST (+ B (CAR P1)) (- (CADR P1 ) V)) "")
 (COMMAND "LINE" (LIST (CAR P1) (- (CADR P1) V)) P1 "")

;LAST BOX
(SETQ Z 0)
(SETQ Z (+ Q R S T U V))
(SETQ Q1 (LIST  (CAR Z1) (- (CADR Z1 ) Z)))
(COMMAND "LINE" Q1 (LIST (+ (CAR Q1) A) (CADR Q1))
                   (LIST (+ (CAR Q1) A) (- (CADR Q1) LA1))
                   (LIST (CAR Q1)       (- (CADR Q1) LA1)) Q1 "")

;INSIDE 1
(SETQ P1 (LIST (+ (CAR Z1) (+ D (/ (- A B) 2)) (/ (- B C D D ) 2))
               (+ (- (CADR Z1 ) Q R S T U V ) W X Y )))
(COMMAND "LINE" P1 (LIST (+ C (CAR P1)) (CADR P1))
(LIST (+ C (CAR P1)) (- (CADR P1 ) W)) "")
(COMMAND "LINE" (LIST (CAR P1) (- (CADR P1) W)) P1 "")
;INSIDE 2
(SETQ P1 (LIST (+ (CAR Z1) (+ D (/ (- A B) 2)) (/ (- B C D D ) 2))
               (+ (- (CADR Z1 ) Q R S T U V ) X Y)))
(COMMAND "LINE" P1 (LIST (+ C (CAR P1)) (CADR P1))
(LIST (+ C (CAR P1)) (- (CADR P1 ) X)) "")
(COMMAND "LINE" (LIST (CAR P1) (- (CADR P1) X)) P1 "")

;INSIDE 3
;(SETQ P1 (LIST (+ (CAR Z1) (+ D (/ (- A B) 2)) (/ (- B C D D ) 2))
;               (+ (- (CADR Z1 ) Q R S T U V ) Y)))

(COMMAND "LAYER" "S" "CENTER" "")
(COMMAND "LINE" (LIST (+ (CAR Z1) (/ A 2)) (+ (CADR Z1) 10))
                (LIST (+ (CAR Z1) (/ A 2)) (- (CADR Z1) 10 Q R S T U V Q)) "")
(SETQ P1 (LIST (+ (CAR Z1) (/ (- A E ) 2)) (- (CADR Z1) Q R S T U )))

; TWO LINE
(COMMAND "LAYER" "S" "DRAW" "")
(SETQ I1 (LIST (CAR Z1) (- (CADR Z1) Q R S T U )))
(SETQ I3 (LIST (-  (+ (CAR I1) A)  D (/ ( - A B) 2)) (CADR I1) ) )
(COMMAND "LINE" I3 (LIST (CAR I3) (- (CADR I3) V)  ) "")

(SETQ I4 (LIST (+ (CAR I1) D (/ ( - A B) 2)) (CADR I1) ) )
(COMMAND "LINE" I4 (LIST (CAR I4) (- (CADR I4) V)  ) "")

;THIRD PICTURE
(SETQ P1 (LIST (+ (CAR W1) 100 A) (CADR W1)))
(SETQ P2 (LIST (+ (CAR P1) A)(CADR P1)))
(SETQ P3 (LIST (CAR P2 ) (- (CADR P2) E)))
(SETQ P4 (LIST (- (CAR P3) A) (CADR P3)))
(SETQ P5 (LIST (/ (+ (CAR P1) (CAR P2)) 2) (+ (CADR P1) 10))) ;CENTER LINE UP
(SETQ P6 (LIST (/ (+ (CAR P3) (CAR P4)) 2) (- (CADR P4) 10)));CENTER LINE DOWN
(SETQ P7 (LIST (- (/ (+ (CAR P1) (CAR P4)) 2) 10) (/ (+ (CADR P1) (CADR P4)) 2)));CENTER LINE LEGT
(SETQ P8 (LIST (+ (/ (+ (CAR P2) (CAR P3)) 2) 10) (/ (+ (CADR P2) (CADR P3)) 2)));RIGHT
(COMMAND "LAYER" "S" "DRAW" "")
(COMMAND "LINE" P1 P2 P3 P4 "C")
(COMMAND "LAYER" "S"  "CENTER" "")
(COMMAND "LINE" P5 P6 "" "LINE" P7 P8 "") ;DRAW CENETR
(SETQ D1 (/ (- A B) 2))
(SETQ D2 (+ (/ (- A B) 2 ) D))
(SETQ D3 (+ (/ (- A B) 2 ) D (/ (- B C  D D ) 2)))
(COMMAND "LAYER" "S" "DRAW" "")
(COMMAND "LINE" (LIST (+ (CAR P5) (/ B 2)) (- (CADR P5) 10)) ;DRAW CENETR RIGTH
                (LIST (+ (CAR P6) (/ B 2)) (+ (CADR P6) 10)) "")
(COMMAND "LINE" (LIST (- (CAR P5) (/ B 2)) (- (CADR P5) 10)) ;DRAW CENETR RIGTH
                (LIST (- (CAR P6) (/ B 2)) (+ (CADR P6) 10)) "")

(COMMAND "LAYER" "S" "CENTER" "")

(SETQ T4 (LIST (+ (CAR C4 ) A 100) (CADR C3 )))
(SETQ T3 (LIST (+ (CAR C3 ) A 100) (CADR C4 )))
(SETQ T2 (LIST (+ (CAR C2 ) A 100) (CADR C1 )))
(SETQ T1 (LIST (+ (CAR C1 ) A 100) (CADR C2 )))
(SETQ Y4 (LIST (+ (CAR Y4 ) A 100) (CADR Y4 )))
(SETQ Y3 (LIST (+ (CAR Y3 ) A 100) (CADR Y3 )))
(SETQ Y2 (LIST (+ (CAR Y2 ) A 100) (CADR Y2 )))
(SETQ Y1 (LIST (+ (CAR Y1 ) A 100) (CADR Y1 )))
(SETQ U4 (LIST (+ (CAR SP4 ) A 100) (CADR SP3 )))
(SETQ U3 (LIST (+ (CAR SP3 ) A 100) (CADR SP4 )))
(SETQ U2 (LIST (+ (CAR SP2 ) A 100) (CADR SP1 )))
(SETQ U1 (LIST (+ (CAR SP1 ) A 100) (CADR SP2 )))

(SETQ GP (ITOA GP))
(SETQ GP-2 (STRCAT "C:\\acad\hon\\G\\G" GP "-1"))
(command "insert" GP-2 T3 1 1 0)
(command "insert" GP-2 T4 1 1 0)
(command "insert" GP-2 T1 1 1 0)
(command "insert" GP-2 T2 1 1 0)

(SETQ SP (ITOA SP))
(SETQ SP-2 (STRCAT "C:\\acad\hon\\G\\SP" SP "-H"))
(command "insert" SP-2 U3 1 1 0)
(command "insert" SP-2 U4 1 1 0)
(command "insert" SP-2 U1 1 1 0)
(command "insert" SP-2 U2 1 1 0)




(SETQ MB (ITOA MB))
(SETQ MB-2 (STRCAT "C:\\acad\hon\\B\\BLT1-" MB))
(command "insert" MB-2 Y4 1 1 0)
(command "insert" MB-2 Y3 1 1 0)
(command "insert" MB-2 Y2 1 1 0)
(command "insert" MB-2 Y1 1 1 0)





;FOURTH PICTURE
;
;CENTER LINE
(COMMAND "LINE" (LIST (+ 100 A (/ E 2) (CAR Z1)) (+ (CADR Z1) 10))
                (LIST (+ 100 A (/ E 2) (CAR Z1)) (- (CADR Z1) 10 Q R S T U V LA1)) "" )
(COMMAND "LAYER" "S" "DRAW" "")
(COMMAND "LINE"
(LIST (+ 100 A (CAR Z1)) (CADR Z1))
(LIST (+ 100 A E (CAR Z1)) (CADR Z1))
(LIST (+ 100 A E (CAR Z1 ) ) (- (CADR Z1) Q R S T U V LA1 ))
(LIST (+ 100 A (CAR Z1 ) ) (- (CADR Z1) Q R S T U V LA1)) "C")
(SETQ Z1 (LIST (+ 100 A (CAR Z1)) (CADR Z1)))
(COMMAND "LINE" (LIST (CAR Z1)       (- (CADR Z1) Q))
                (LIST (+ (CAR Z1) E) (- (CADR Z1) Q)) "")
(COMMAND "LINE" (LIST (CAR Z1)       (- (CADR Z1) (+ Q R )))
                (LIST (+ (CAR Z1) E) (- (CADR Z1) (+ Q R ))) "")
(COMMAND "LINE" (LIST (CAR Z1)       (- (CADR Z1) (+ Q R S)))
                (LIST (+ (CAR Z1) E) (- (CADR Z1) (+ Q R S))) "")



(COMMAND "LINE" (LIST (CAR Z1)       (- (CADR Z1) (+ Q R S T)))
                (LIST (+ (CAR Z1) E) (- (CADR Z1) (+ Q R S T))) "")

(COMMAND "LINE" (LIST (CAR Z1)       (- (CADR Z1) (+ Q R S T U)))
                (LIST (+ (CAR Z1) E) (- (CADR Z1) (+ Q R S T U ))) "")

(COMMAND "LINE" (LIST (CAR Z1)       (- (CADR Z1) (+ Q R S T U V)))
                (LIST (+ (CAR Z1) E) (- (CADR Z1) (+ Q R S T U V))) "")

(COMMAND "MENU" "ACAD4")

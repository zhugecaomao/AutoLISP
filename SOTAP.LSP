(defun c:sotap()
(setq F (getvar "blipmode")) (setvar "blipmode" 0)
(setq p (getpoint "Insert point:"))
(setq D (getint "\n Enter screw size [4] [6] [8] [10] [12] [16] [20] [22]:"))
(if (= D 4)(setq D1 3.2))
(if (= D 6)(setq D1 5.0))
(if (= D 8)(setq D1 6.6))
(if (= D 10)(setq D1 8.4))
(if (= D 12)(setq D1 10.0))
(if (= D 16)(setq D1 13.8))
(if (= D 20)(setq D1 17.5))
(if (= D 22)(setq D1 17.5))
(command "circle" p "D" D)
(command "circle" p "D" D1)
(setvar "blipmode" F))

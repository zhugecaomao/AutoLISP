defun c:SP3
;THE POINT IS FIST COUNTER Y THEN X
(COMMAND "SETVAR" "CMDECHO" 0)
;(IF (= (TYPE F1) 'FILE ) "YES"  (STOP))
;(IF (= (TYPE F2) 'FILE ) "YES" (STOP))
(setq SPSET (findfile "c:/acad/ACAD/SUPPORT/SP.SET"))
(IF (= SPSET NIL)
    (PROGN
       (PROMPT "\nPLEASE SETTING LAYER SUPPORT :" )
       (SETQ FC (OPEN "c:/acad/ACAD/SUPPORT/SP.SET" "w"))
       (setq SPCNT (GETSTRING T"\nSETTING SUPPORT  LAYER OF CONTNIUE LINE/<0>:"))
       (IF (= SPCNT "")
              (WRITE-LINE "0" FC)
              (WRITE-LINE SPCNT FC)
       )
       (setq SPCEN (GETSTRING T"\nSETTING SUPPORT LAYER OF CENTER LINE/<CEN>:"))
       (IF (= SPCEN "")
              (WRITE-LINE "CEN" FC)
              (WRITE-LINE SPCEN FC)
       )
       (setq SPHID (GETSTRING T"\nSETTING SUPPORT LAYER OF HIDDEN LINE/<HID>:"))
       (IF (= SPHID "")
              (WRITE-LINE "HID" FC)
              (WRITE-LINE SPHID FC)
       )
       (setq SPBLC (GETSTRING T"\nSETTING SKT-BLT LAYER OF CONTINUE LINE /<0>:"))
       (IF (= SPBLC "")
              (WRITE-LINE "0" FC)
              (WRITE-LINE SPBLC FC)
       )
       (setq SPBLH (GETSTRING T"\nSETTING SKT-BLT LAYER OF HIDDEN LINE /<HID>:"))
       (IF (= SPBLH "")
              (WRITE-LINE "HID" FC)
              (WRITE-LINE SPBLH FC)
       )
       (setq SPTXT (GETSTRING T"\nSETTING SUPPORT LAYER OF TEXT /<TEXT>:"))
       (IF (= SPTXT "")
              (WRITE-LINE "TEXT" FC)
              (WRITE-LINE SPTXT FC)
       )
       (setq SPTXT (GETSTRING T"\nSETTING SUPPORT LAYER OF DIM /<DIM1>:"))
       (IF (= SPDIM "")
              (WRITE-LINE "DIM1" FC)
              (WRITE-LINE SPDIM FC)
       )
       (CLOSE FC)
    )
)

(IF (/= SPSET NIL)
    (PROGN
       (SETQ FC (OPEN "c:/acad/ACAD/SUPPORT/SP.SET" "r"))
       (SETQ SPCNT (READ-LINE FC))
       (SETQ SPCEN (READ-LINE FC))
       (SETQ SPHID (READ-LINE FC))
       (SETQ SPBLC (READ-LINE FC))
       (SETQ SPBLH (READ-LINE FC))
       (SETQ SPTXT (READ-LINE FC))
       (SETQ SPDIM (READ-LINE FC))
       (IF (OR (= SPCNT "") (= SPCEN "") (= SPHID "") (= SPBLC "") (= SPBLH "")(= SPTXT "") (= SPDIM "")
               (= SPCNT NIL) (= SPCEN NIL) (= SPHID NIL) (= SPBLC NIL) (= SPBLH NIL) (= SPTXT NIL) (= SPDIM NIL))
           (CLOSE FC)
       )
       (IF (OR (= SPCNT "") (= SPCEN "") (= SPHID "") (= SPBLC "") (= SPBLH "")(= SPTXT "") (= SPDIM "")
               (= SPCNT NIL) (= SPCEN NIL) (= SPHID NIL) (= SPBLC NIL) (= SPBLH NIL) (= SPTXT NIL) (= SPDIM NIL))
           (PROGN
              (PROMPT "\nPLEASE SETTING LAYER SUPPORT:" )
              (SETQ FC (OPEN "c:/acad/ACAD/SUPPORT/SP.SET" "w"))
              (setq SPCNT (GETSTRING T"\nSETTING SUPPORT LAYER OF CONTNIUE LINE/<0>:"))
              (IF (= SPCNT "")
                  (WRITE-LINE "0" FC)
                  (WRITE-LINE SPCNT FC)
              )
              (setq SPCEN (GETSTRING T"\nSETTING SUPPORT LAYER OF CENTER LINE/<CEN>:"))
              (IF (= SPCEN "")
                  (WRITE-LINE "CEN" FC)
                  (WRITE-LINE SPCEN FC)
              )
              (setq SPHID (GETSTRING T"\nSETTING SUPPORT LAYER OF HIDDEN LINE/<HID>:"))
              (IF (= SPHID "")
                  (WRITE-LINE "HID" FC)
                  (WRITE-LINE SPHID FC)
              )
              (setq SPBLC (GETSTRING T"\nSETTING SKT-BLT LAYER OF CONTINUE LINE /<0>:"))
              (IF (= SPBLC "")
                  (WRITE-LINE "0" FC)
                  (WRITE-LINE SPBLC FC)
              )
              (setq SPBLH (GETSTRING T"\nSETTING SKT-BLT LAYER OF HIDDEN LINE /<HID>:"))
              (IF (= SPBLH "")
                  (WRITE-LINE "HID" FC)
                  (WRITE-LINE SPBLH FC)
              )
              (setq SPTXT (GETSTRING T"\nSETTING SUPPORT LAYER OF TEXT /<TEXT>:"))
              (IF (= SPTXT "")
                  (WRITE-LINE "TEXT" FC)
                  (WRITE-LINE SPTXT FC)
              )
              (setq SPDIM (GETSTRING T"\nSETTING SUPPORT LAYER OF DIM /<DIM1>:"))
              (IF (= SPDIM "")
                  (WRITE-LINE "DIM1" FC)
                  (WRITE-LINE SPDIM FC)
              )
           (CLOSE FC)
           )
       )
       (SETQ FC (OPEN "c:/acad/ACAD/SUPPORT/SP.SET" "r"))
       (SETQ SPCNT (READ-LINE FC))
       (SETQ SPCEN (READ-LINE FC))
       (SETQ SPHID (READ-LINE FC))
       (SETQ SPBLC (READ-LINE FC))
       (SETQ SPBLH (READ-LINE FC))
       (SETQ SPTXT (READ-LINE FC))
       (SETQ SPDIM (READ-LINE FC))
       (CLOSE FC)
       (PROMPT "\nSUPPORT CONTINUE OF LAYER IS:" )(PROMPT SPCNT)(TERPRI)
       (PROMPT "\nSUPPORT CENTER OF LAYER IS:" ) (PROMPT SPCEN)(TERPRI)
       (PROMPT "\nSUPPORT HIDDEN OF LAYER IS:" ) (PROMPT SPHID)(TERPRI)
       (PROMPT "\nSKT-BLT CONTINUE LAYER IS:" ) (PROMPT SPBLC)(TERPRI)
       (PROMPT "\nSKT-BLT HIDDEN   LAYER IS:" ) (PROMPT SPBLH)(TERPRI)
       (PROMPT "\nSUPPORT TEXT   OF LAYER IS:" ) (PROMPT SPTXT)(TERPRI)
       (PROMPT "\nSUPPORT DIM    OF LAYER IS:" ) (PROMPT SPDIM)(TERPRI)
    )
)

(SETQ ANS (strcase (GETSTRING "\nDO YOU WANT TO CHANGE LAST SETTING <Y/N> N:")))
(IF (= ANS "Y")
    (PROGN
       (PROMPT "\nPLEASE SETTING LAYER:" )
       (SETQ FC (OPEN "c:/acad/ACAD/SUPPORT/SP.SET" "w"))
       (PROMPT "\nSUPPORT CONTINUE OF LAYER <" )(PROMPT SPCNT)(PROMPT">:")
       (setq SPCNT (GETSTRING T))
       (IF (= SPCNT "")
              (WRITE-LINE "0" FC)
              (WRITE-LINE SPCNT FC)
       )
       (PROMPT "\nSUPPORT CENTER OF LAYER <" )(PROMPT SPCEN)(PROMPT">:")
       (setq SPCEN (GETSTRING T))
       (IF (= SPCEN "")
              (WRITE-LINE "CEN" FC)
              (WRITE-LINE SPCEN FC)
       )
       (PROMPT "\nSUPPORT HIDDEN OF LAYER <" )(PROMPT SPHID)(PROMPT">:")
       (setq SPHID (GETSTRING T))
       (IF (= SPHID "")
              (WRITE-LINE "HID" FC)
              (WRITE-LINE SPHID FC)
       )
       (PROMPT "\nSKT-BLT LAYER OF CONTINUE LINE <" )(PROMPT SPBLC)(PROMPT">:")
       (setq SPBLC (GETSTRING T))
       (IF (= SPBLC "")
              (WRITE-LINE "0" FC)
              (WRITE-LINE SPBLC FC)
       )
       (PROMPT "\nSKT-BLT LAYER OF HIDDEN LINE <" )(PROMPT SPBLH)(PROMPT">:")
       (setq SPBLH (GETSTRING T))
       (IF (= SPBLH "")
              (WRITE-LINE "HID" FC)
              (WRITE-LINE SPBLH FC)
       )
       (PROMPT "\nTEXT OF LAYER <" )(PROMPT SPTXT)(PROMPT">:")
       (setq SPTXT (GETSTRING T))
       (IF (= SPTXT "")
              (WRITE-LINE "TEXT" FC)
              (WRITE-LINE SPTXT FC)
       )
       (PROMPT "\nDIM OF LAYER <" )(PROMPT SPDIM)(PROMPT">:")
       (setq SPDIM (GETSTRING T))
       (IF (= SPDIM "")
              (WRITE-LINE "DIM1" FC)
              (WRITE-LINE SPDIM FC)
       )
       (CLOSE FC)
       (SETQ FC (OPEN "c:/acad/ACAD/SUPPORT/SP.SET" "r"))
       (SETQ SPCNT (READ-LINE FC))
       (SETQ SPCEN (READ-LINE FC))
       (SETQ SPHID (READ-LINE FC))
       (SETQ SPBLC (READ-LINE FC))
       (SETQ SPBLH (READ-LINE FC))
       (SETQ SPTXT (READ-LINE FC))
       (SETQ SPDIM (READ-LINE FC))
       (CLOSE FC)
       (PROMPT "\nSUPPORT CONTINUE OF LAYER NOW IS:" )(PROMPT SPCNT)(TERPRI)
       (PROMPT "\nSUPPORT CENTER   OF LAYER NOW IS:" ) (PROMPT SPCEN)(TERPRI)
       (PROMPT "\nSUPPORT HIDDEN   OF LAYER NOW IS:" ) (PROMPT SPHID)(TERPRI)
       (PROMPT "\nSKT-BLT  CONTINUE OF LAYER NOW IS:" ) (PROMPT SPBLC)(TERPRI)
       (PROMPT "\nSKT-BLT  HIDDEN   OF LAYER NOW IS:" ) (PROMPT SPBLH)(TERPRI)
       (PROMPT "\nTEXT OF LAYER IS:" ) (PROMPT SPTXT)(TERPRI)
       (PROMPT "\nDIM  OF LAYER IS:" ) (PROMPT SPDIM)(TERPRI)
  )
)



(MENUCMD "S=SPT")
(COMMAND "LAYER" "SET" SPCNT "")
(SETQ SD (GETREAL"\nSelect SUPPORT dim:"))
(IF (>= SD 50)
    (SETQ D 12)
    (SETQ D 10)
)
(GRAPHSCR) (TERPRI)                                     ;GRAPHICS MODE
;(COMMAND "UJ" "")
(IF  (= (SETQ ANS (GETSTRING "\nDOU YOU WANT TO TRIM P3 P4 LINE:<Y>")) "")
     (SETQ ANS "Y"))
(SETQ ANS (STRCASE ANS))
(IF (= D 3)
    (PROGN
       (SETQ D2 3.3)
       (SETQ BD1 5)
       (SETQ BD2 6)
       (SETQ H1  3)
       (SETQ H2  4)
       (SETQ SP 0.25)
    )
)
(IF (= D 4)
    (PROGN
       (SETQ D2 4.5)
       (SETQ BD1 6.5)
       (SETQ BD2 7.5)
       (SETQ H1  4)
       (SETQ H2  5)
       (SETQ SP 0.35)
    )
)
(IF (= D 5)
    (PROGN
       (SETQ D2 5.5)
       (SETQ BD1 8)
       (SETQ BD2 9)
       (SETQ H1  5)
       (SETQ H2  6.5)
       (SETQ SP 0.4)
    )
)
(IF (= D 6)
    (PROGN
       (SETQ D2 6.5)
       (SETQ BD1 10)
       (SETQ BD2 11)
       (SETQ H1  6)
       (SETQ H2  6.5)
       (SETQ SP 0.5)
    )
)
(IF (= D 8)
    (PROGN
       (SETQ D2 8.8)
       (SETQ BD1 13)
       (SETQ BD2 14)
       (SETQ H1  8)
       (SETQ H2  8.6)
       (SETQ SP 0.63)
    )
)
(IF (= D 10)
    (PROGN
       (SETQ D2 11)
       (SETQ BD1 16)
       (SETQ BD2 17.5)
       (SETQ H1  10)
       (SETQ H2  10.8)
       (SETQ SP 0.75)
    )
)
(IF (= D 12)
    (PROGN
       (SETQ D2 13)
       (SETQ BD1 18)
       (SETQ BD2 20)
       (SETQ H1  12)
       (SETQ H2  13)
       (SETQ SP 0.88)
    )
)
(IF (= D 14)
    (PROGN
       (SETQ D2 15.5)
       (SETQ BD1 21)
       (SETQ BD2 23)
       (SETQ H1  14)
       (SETQ H2  15)
       (SETQ SP 1.0)
    )
)
(IF (= D 16)
    (PROGN
       (SETQ D2 18)
       (SETQ BD1 24)
       (SETQ BD2 26)
       (SETQ H1  16)
       (SETQ H2  17.5)
       (SETQ SP 1.0)
    )
)
(IF (= D 20)
    (PROGN
       (SETQ D2 22)
       (SETQ BD1 28)
       (SETQ BD2 30)
       (SETQ H1  20)
       (SETQ H2  21.5)
       (SETQ SP 1.25)
    )
)
(IF (= D 22)
    (PROGN
       (SETQ D2 24)
       (SETQ BD1 30)
       (SETQ BD2 32)
       (SETQ H1  22)
       (SETQ H2  23.5)
       (SETQ SP 1.25)
    )
)
(IF (= D 24)
    (PROGN
       (SETQ D2 26)
       (SETQ BD1 33)
       (SETQ BD2 35)
       (SETQ H1  24)
       (SETQ H2  25.5)
       (SETQ SP 1.5)
    )
)
(IF (= D 30)
    (PROGN
       (SETQ D2 33)
       (SETQ BD1 42)
       (SETQ BD2 45)
       (SETQ H1  30)
       (SETQ H2  32)
       (SETQ SP 1.75)
    )
)
(IF (= D 36)
    (PROGN
       (SETQ D2 39)
       (SETQ BD1 50)
       (SETQ BD2 54)
       (SETQ H1  36)
       (SETQ H2  38)
       (SETQ SP 1.75)
    )
)
;(SETQ P1 (LIST 440.24 542.26))
;(SETQ P2 (LIST 440.24 572.26))
;(SETQ P3 (LIST 440.24 597.26))
;(SETQ P4 (LIST 440.24 617.36))
;(SETQ P5 (LIST 440.24 672.36))
(SETQ P1 (GETPOINT "\nP1:"))
(SETQ P2 (GETPOINT P1 "\nP2:"))
(SETQ P3 (GETPOINT P2 "\nP3:"))
(SETQ P4 (GETPOINT P3 "\nP4:"))
(SETQ P5 (GETPOINT P4 "\nP5:"))
(SETQ AG1 (ANGLE P1 P2))
(SETQ AG2 (* PI 0.5))
(SETQ LSE (DISTANCE P1 P2)) ;DIST FOR P1 P2
(SETQ LS5 (DISTANCE P1 P5)) ;DIST FOR P1 P5
(SETQ LS2 (DISTANCE P1 P2)) ;DIST FOR P1 P2
(SETQ LS3 (DISTANCE P1 P3)) ;DIST FOR P1 P3
(SETQ LS4 (DISTANCE P1 P4)) ;DIST FOR P1 P4
(SETQ CR SP)
(SETQ DR1 (POLAR P1 (+ AG1 AG2) (/ BD2 2.0)))
(SETQ DR2 (POLAR P1 (- AG1 AG2) (/ BD2 2.0)))
(SETQ DR3 (POLAR (POLAR P1 AG1 H2) (+ AG1 AG2) (/ BD2 2.0)))
(SETQ DR4 (POLAR (POLAR P1 AG1 H2) (- AG1 AG2) (/ BD2 2.0)))
(SETQ DR5 (POLAR (POLAR P1 AG1 (- H2 H1)) (+ AG1 AG2) (- (/ BD1 2.0) SP)))
(SETQ DR6 (POLAR (POLAR P1 AG1 (- H2 H1)) (- AG1 AG2) (- (/ BD1 2.0) SP)))
(SETQ DR7 (POLAR (POLAR P1 AG1 (+ (- H2 H1) SP)) (+ AG1 AG2) (/ BD1 2.0)))
(SETQ DR8 (POLAR (POLAR P1 AG1 (+ (- H2 H1) SP)) (- AG1 AG2) (/ BD1 2.0)))
(SETQ DR9 (POLAR (POLAR P1 AG1 H2) (+ AG1 AG2) (/ BD1 2.0)))
(SETQ DR10 (POLAR (POLAR P1 AG1 H2) (- AG1 AG2) (/ BD1 2.0)))
(SETQ DR11 (POLAR (POLAR P1 AG1 H2) (+ AG1 AG2) (/ D2 2.0)))
(SETQ DR12 (POLAR (POLAR P1 AG1 H2) (- AG1 AG2) (/ D2 2.0)))
(SETQ DR13 (POLAR (POLAR P1 AG1 LS5) (+ AG1 AG2) (/ D2 2.0)))
(SETQ DR14 (POLAR (POLAR P1 AG1 LS5) (- AG1 AG2) (/ D2 2.0)))
(SETQ DR15 (POLAR (POLAR P1 AG1 H2) (+ AG1 AG2) (/ D 2.0)))
(SETQ DR16 (POLAR (POLAR P1 AG1 H2) (- AG1 AG2) (/ D 2.0)))
(SETQ DR17 (POLAR (POLAR P1 AG1 (- (+ LS5 (* D 2)) SP)) (+ AG1 AG2) (/ D 2.0)))
(SETQ DR18 (POLAR (POLAR P1 AG1 (- (+ LS5 (* D 2)) SP)) (- AG1 AG2) (/ D 2.0)))
(SETQ DR19 (POLAR (POLAR P1 AG1 (+ LS5 (* D 2))) (+ AG1 AG2) (- (/ D 2.0) SP)))
(SETQ DR20 (POLAR (POLAR P1 AG1 (+ LS5 (* D 2))) (- AG1 AG2) (- (/ D 2.0) SP)))
(SETQ DR21 (POLAR (POLAR P1 AG1 (- LS5 (* D 0.25))) (+ AG1 AG2) (/ D 2.0)))
(SETQ DR22 (POLAR (POLAR P1 AG1 (- LS5 (* D 0.25))) (- AG1 AG2) (/ D 2.0)))
(SETQ DR23 (POLAR (POLAR P1 AG1 (- LS5 (* D 0.25))) (+ AG1 AG2) (- (/ D 2.0) SP)))
(SETQ DR24 (POLAR (POLAR P1 AG1 (- LS5 (* D 0.25))) (- AG1 AG2) (- (/ D 2.0) SP)))
(SETQ DR25 (POLAR (POLAR P1 AG1 (- LS5 (* D 0.25) SP)) (+ AG1 AG2) (/ D 2.0)))
(SETQ DR26 (POLAR (POLAR P1 AG1 (- LS5 (* D 0.25) SP)) (- AG1 AG2) (/ D 2.0)))
(SETQ SINT (POLAR (POLAR P1 AG1 (+ LS5 (* D 2))) AG1 (/ D 2.0)))
(SETQ DRINT1 (POLAR SINT (+ AG1 (DTR 120)) 3))
(SETQ DRINT2 (POLAR SINT (- AG1 (DTR 120)) 3))
(SETQ INT1 (INTERS SINT DRINT1 DR19 DR23 NIL))
(SETQ INT2 (INTERS SINT DRINT2 DR20 DR24 NIL))


(SETQ DR27 (POLAR (POLAR P1 AG1 (+ LS5 (* D 1.5))) (+ AG1 AG2) (- (/ D 2.0) SP)))
(SETQ DR28 (POLAR (POLAR P1 AG1 (+ LS5 (* D 1.5))) (- AG1 AG2) (- (/ D 2.0) SP)))
(SETQ DR29 (POLAR (POLAR P1 AG1 (- (+ LS5 (* D 1.5)) SP)) (+ AG1 AG2) (/ D 2.0)))
(SETQ DR30 (POLAR (POLAR P1 AG1 (- (+ LS5 (* D 1.5)) SP)) (- AG1 AG2) (/ D 2.0)))
;END OF BLT

(SETQ DR31 (POLAR P2 (+ AG1 AG2) (- (/ SD 2.0) 1)))
(SETQ DR32 (POLAR P2 (- AG1 AG2) (- (/ SD 2.0) 1)))
(SETQ DR33 (POLAR (POLAR P2 AG1 1) (+ AG1 AG2) (/ SD 2.0)))
(SETQ DR34 (POLAR (POLAR P2 AG1 1) (- AG1 AG2) (/ SD 2.0)))

(SETQ DR35 (POLAR (POLAR P1 AG1 (- LS5 1)) (+ AG1 AG2) (/ SD 2.0)))
(SETQ DR36 (POLAR (POLAR P1 AG1 (- LS5 1)) (- AG1 AG2) (/ SD 2.0)))

(SETQ DR37 (POLAR (POLAR P1 AG1 LS5 ) (+ AG1 AG2) (- (/ SD 2.0) 1)))
(SETQ DR38 (POLAR (POLAR P1 AG1 LS5 ) (- AG1 AG2) (- (/ SD 2.0) 1)))

(SETQ DR39 (POLAR (POLAR P1 AG1 LS2 ) (+ AG1 AG2) (+ (/ SD 2.0) 1.5)))
(SETQ DR40 (POLAR (POLAR P1 AG1 LS2 ) (- AG1 AG2) (+ (/ SD 2.0) 1.5)))
(SETQ DR41 (POLAR (POLAR P1 AG1 LS4 ) (+ AG1 AG2) (+ (/ SD 2.0) 1.5)))
(SETQ DR42 (POLAR (POLAR P1 AG1 LS4 ) (- AG1 AG2) (+ (/ SD 2.0) 1.5)))
;

(COMMAND "LINE" DR31 DR33 "")
(COMMAND "LINE" DR32 DR34 "")
(COMMAND "LINE" DR33 DR34 "")
(COMMAND "LINE" DR33 DR35 "")
(COMMAND "LINE" DR34 DR36 "")
(COMMAND "LINE" DR35 DR37 "")
(COMMAND "LINE" DR36 DR38 "")
(COMMAND "LINE" DR35 DR36 "")
(COMMAND "LINE" DR39 DR41 "")
(COMMAND "LINE" DR40 DR42 "")
(COMMAND "SETVAR" "PICKBOX" 1)
(IF (= ANS "Y")
    (COMMAND "TRIM" DR33 DR34 "" (POLAR P3 (+ AG1 AG2) 1) "")
)
(IF (= ANS "Y")
    (COMMAND "TRIM" DR33 DR34 "" (POLAR P4 (+ AG1 AG2) 1) "")
)


(COMMAND "LAYER" "SET" SKCNT "")
(COMMAND "LINE" DR1 DR3 DR4 DR2 "")
(COMMAND "LINE" DR5 DR7 "")
(COMMAND "LINE" DR6 DR8 "")
(COMMAND "LINE" DR5 DR6 "")
(COMMAND "LINE" DR7 DR8 "")
(COMMAND "LINE" DR7 DR9 "")
(COMMAND "LINE" DR8 DR10 "")
(COMMAND "LINE" DR11 DR13 "")
(COMMAND "LINE" DR12 DR14 "")
(COMMAND "LINE" DR15 DR17 "")
(COMMAND "LINE" DR16 DR18 "")
(COMMAND "LINE" DR17 DR19 "")
(COMMAND "LINE" DR18 DR20 "")
(COMMAND "LINE" DR19 DR20 "")
(COMMAND "LINE" DR21 DR22 "")
(COMMAND "LINE" DR25 DR23 INT1 "")
(COMMAND "LINE" DR26 DR24 INT2 "")
(COMMAND "LINE" SINT INT1 "")
(COMMAND "LINE" SINT INT2 "")
(COMMAND "LINE" INT1 INT2 "")
(COMMAND "LINE" DR27 DR29 "")
(COMMAND "LINE" DR28 DR30 "")
(COMMAND "LINE" DR27 DR28 "")
(COMMAND "LINE" DR29 DR30 "")
;
(COMMAND "LAYER" "SET" SPCEN "")
(COMMAND "LINE" (POLAR P1 AG1 -1) (POLAR P1 AG1 (+ LS5  (* 2.5 D) 1)) "")
(COMMAND "SETVAR" "PICKBOX" 3)

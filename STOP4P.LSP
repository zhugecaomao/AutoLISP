(defun c:stop4()
;(COMMAND "LAYER" "S" "0" "")
;(COMMAND "VSLIDE" "STOP2" )
(SETQ NLY (GETVAR "CLAYER"))
(setq STOP2SET (findfile "C:/ACAD/hon/set/STOP2.SET"))
(IF (= STOP2SET NIL)
    (PROGN
       (PROMPT "\nPLEASE SETTING LAYER STOP2 :" )
       (SETQ FC (OPEN "C:/ACAD/hon/set/STOP2.SET" "w"))
       (setq STOP2CNT (GETSTRING T"\nSETTING STOP2 LAYER OF CONTNIUE LINE/<DRAW>:"))
       (IF (= STOP2CNT "")
              (WRITE-LINE "DRAW" FC)
              (WRITE-LINE STOP2CNT FC)
       )
       (setq STOP2CEN (GETSTRING T"\nSETTING STOP2 LAYER OF CENTER LINE/<CENTER>:"))
       (IF (= STOP2CEN "")
              (WRITE-LINE "CENTER" FC)
              (WRITE-LINE STOP2CEN FC)
       )
       (setq STOP2HID (GETSTRING T"\nSETTING STOP2 LAYER OF HIDDEN LINE/<HIDDEN>:"))
       (IF (= STOP2HID "")
              (WRITE-LINE "HIDDEN" FC)
              (WRITE-LINE STOP2HID FC)
       )
       (setq STOP2DIM (GETSTRING T"\nSETTING STOP2 LAYER OF DIMESION /<TEXT>:"))
       (IF (= STOP2DIM "")
              (WRITE-LINE "TEXT" FC)
              (WRITE-LINE STOP2DIM FC)
       )
       (setq STOP2TXT (GETSTRING T"\nSETTING STOP2 LAYER OF TEXT /<TEXT>:"))
       (IF (= STOP2TXT "")
              (WRITE-LINE "TEXT" FC)
              (WRITE-LINE STOP2TXT FC)
       )
       (CLOSE FC)
    )
)

(IF (/= STOP2SET NIL)
    (PROGN
       (SETQ FC (OPEN "C:/ACAD/hon/set/STOP2.SET" "r"))
       (SETQ STOP2CNT (READ-LINE FC))
       (SETQ STOP2CEN (READ-LINE FC))
       (SETQ STOP2HID (READ-LINE FC))
       (SETQ STOP2DIM (READ-LINE FC))
       (SETQ STOP2TXT (READ-LINE FC))
       (IF (OR (= STOP2CNT "") (= STOP2CEN "") (= STOP2HID "") (= STOP2DIM "") (= STOP2TXT "")
               (= STOP2CNT NIL) (= STOP2CEN NIL) (= STOP2HID NIL) (= STOP2DIM NIL) (= STOP2TXT NIL))
           (CLOSE FC)
       )
       (IF (OR (= STOP2CNT "") (= STOP2CEN "") (= STOP2HID "") (= STOP2DIM "") (= STOP2TXT "")
               (= STOP2CNT NIL) (= STOP2CEN NIL) (= STOP2HID NIL) (= STOP2DIM NIL) (= STOP2TXT NIL))
           (PROGN
              (PROMPT "\nPLEASE SETTING LAYER OF SCREW :" )
              (SETQ FC (OPEN "C:/ACAD/hon/set/STOP2.SET" "w"))
              (setq STOP2CNT (GETSTRING T"\nSETTING STOP2 LAYER OF CONTNIUE LINE/<DRAW>:"))
              (IF (= STOP2CNT "")
                  (WRITE-LINE "DRAW" FC)
                  (WRITE-LINE STOP2CNT FC)
              )
              (setq STOP2CEN (GETSTRING T"\nSETTING STOP2 LAYER OF CENTER LINE/<CENTER>:"))
              (IF (= STOP2CEN "")
                  (WRITE-LINE "CENTER" FC)
                  (WRITE-LINE STOP2CEN FC)
              )
              (setq STOP2HID (GETSTRING T"\nSETTING STOP2 LAYER OF HIDDEN LINE/<HIDDEN>:"))
              (IF (= STOP2HID "")
                  (WRITE-LINE "HIDDEN" FC)
                  (WRITE-LINE STOP2HID FC)
              )
              (setq STOP2DIM (GETSTRING T"\nSETTING STOP2 LAYER OF DIMESION/<TEXT>:"))
              (IF (= STOP2DIM "")
                  (WRITE-LINE "TEXT" FC)
                  (WRITE-LINE STOP2DIM FC)
              )
              (setq STOP2TXT (GETSTRING T"\nSETTING STOP2 LAYER OF TEXT /<TEXT>:"))
              (IF (= STOP2TXT "")
                  (WRITE-LINE "TEXT" FC)
                  (WRITE-LINE STOP2TXT FC)
              )
           (CLOSE FC)
           )
       )
       (SETQ FC (OPEN "C:/ACAD/hon/set/STOP2.SET" "r"))
       (SETQ STOP2CNT (READ-LINE FC))
       (SETQ STOP2CEN (READ-LINE FC))
       (SETQ STOP2HID (READ-LINE FC))
       (SETQ STOP2DIM (READ-LINE FC))
       (SETQ STOP2TXT (READ-LINE FC))
       (CLOSE FC)
       (PROMPT "\nSCREW CONTINUE OF LAYER IS:" )(PROMPT STOP2CNT)(TERPRI)
       (PROMPT "\nSCREW CENTER OF LAYER IS:" ) (PROMPT STOP2CEN)(TERPRI)
       (PROMPT "\nSCREW HIDDEN OF LAYER IS:" ) (PROMPT STOP2HID)(TERPRI)
       (PROMPT "\nSCREW DIMENSION OF LAYER IS:" ) (PROMPT STOP2DIM)(TERPRI)
       (PROMPT "\nSCREW TEXT   OF LAYER IS:" ) (PROMPT STOP2TXT)(TERPRI)
    )
)


(SETQ ANS (strcase (GETSTRING "\nDO YOU WANT TO CHANGE LAST SETTING <Y/N> N:")))
(IF (= ANS "Y")
    (PROGN
       (PROMPT "\nPLEASE SETTING LAYER:" )
       (SETQ FC (OPEN "C:/ACAD/hon/set/STOP2.SET" "w"))
       (PROMPT "\nSCREW CONTINUE OF LAYER <" )(PROMPT STOP2CNT)(PROMPT">:")
       (setq STOP2CNT (GETSTRING T))
       (IF (= STOP2CNT "")
              (WRITE-LINE "DRAW" FC)
              (WRITE-LINE STOP2CNT FC)
       )
       (PROMPT "\nSCREW CENTER OF LAYER <" )(PROMPT STOP2CEN)(PROMPT">:")
       (setq STOP2CEN (GETSTRING T))
       (IF (= STOP2CEN "")
              (WRITE-LINE "CENTER" FC)
              (WRITE-LINE STOP2CEN FC)
       )
       (PROMPT "\nSCREW HIDDEN OF LAYER <" )(PROMPT STOP2HID)(PROMPT">:")
       (setq STOP2HID (GETSTRING T))
       (IF (= STOP2HID "")
              (WRITE-LINE "HIDDEN" FC)
              (WRITE-LINE STOP2HID FC)
       )
       (PROMPT "\nSCREW DIMESION OF LAYER <" )(PROMPT STOP2DIM)(PROMPT">:")
       (setq STOP2DIM (GETSTRING T))
       (IF (= STOP2DIM "")
              (WRITE-LINE "TEXT" FC)
              (WRITE-LINE STOP2DIM FC)
       )
       (PROMPT "\nSCREW TEXT OF LAYER <" )(PROMPT STOP2TXT)(PROMPT">:")
       (setq STOP2TXT (GETSTRING T))
       (IF (= STOP2TXT "")
              (WRITE-LINE "TEXT" FC)
              (WRITE-LINE STOP2TXT FC)
       )
       (CLOSE FC)
       (SETQ FC (OPEN "C:/ACAD/hon/set/STOP2.SET" "r"))
      (SETQ STOP2CNT (READ-LINE FC))
       (SETQ STOP2CEN (READ-LINE FC))
       (SETQ STOP2HID (READ-LINE FC))
       (SETQ STOP2DIM (READ-LINE FC))
       (SETQ STOP2TXT (READ-LINE FC))
       (CLOSE FC)
       (PROMPT "\nSCREW CONTINUE OF LAYER NOW IS:" )(PROMPT STOP2CNT)(TERPRI)
       (PROMPT "\nSCREW CENTER   OF LAYER NOW IS:" ) (PROMPT STOP2CEN)(TERPRI)
       (PROMPT "\nSCREW HIDDEN   OF LAYER NOW IS:" ) (PROMPT STOP2HID)(TERPRI)
       (PROMPT "\nSCREW DIM      OF LAYER NOW IS:" ) (PROMPT STOP2DIM)(TERPRI)
       (PROMPT "\nSCREW TEXT     OF LAYER NOW  IS:" ) (PROMPT STOP2TXT)(TERPRI)
  )
)
(SETQ DIM (GETREAL"\nPLEASE SLECT THE DIM OF THE ENTITY:(DIM3~DIM8)::"))
(IF (OR ( = DIM "") (= DIM NIL) )
(PROGN
     (SETQ DIM 3 )
     ))
(SETQ P1 (GETPOINT"\n SLECT THE FIRST BASE POINT:"))
(SETQ P2 (GETPOINT P1"\n SELECT THE SECOND BASE POINT:"))
;(SETQ MI (GETREAL"\n SELECT THE DIM VALUE :"))

 (IF (= DIM 3 )
(PROGN
  ( SETQ A 0.8 )
  (SETQ D  6  )
  (SETQ C 0.25 )
  (SETQ B 0.7  )
  (SETQ H 1.75 )
  (SETQ S 12 )
  (SETQ P 0.6 )
  (SETQ Dd 7  )
  (SETQ Ddd 3.4 )
  (SETQ Hh  1.8 )
))

 (IF (= DIM 4 )
(PROGN
  ( SETQ A 1.0 )
  (SETQ D  8  )
  (SETQ C 0.3  )
  (SETQ B 0.9  )
  (SETQ H 2.3  )
  (SETQ S 16 )
  (SETQ P 0.75 )
  (SETQ Dd  9.3 )
  (SETQ Ddd 4.5 )
  (SETQ Hh  2.4 )
))
 (IF (= DIM 5 )
(PROGN
  ( SETQ A 1.2 )
  (SETQ D  10 )
  (SETQ C 0.3  )
  (SETQ B 1.1  )
  (SETQ H 2.8  )
  (SETQ S 20 )
  (SETQ P 0.9 )
  (SETQ Dd 11.5 )
  (SETQ Ddd 5.5 )
  (SETQ Hh  3   )
))

 (IF (= DIM 6 )
(PROGN
  ( SETQ A 1.2 )
  (SETQ D  12 )
  (SETQ C 0.4  )
  (SETQ B 1.4  )
  (SETQ H 3.4  )
  (SETQ S 25 )
  (SETQ P 1   )
  (SETQ Dd 13.7 )
  (SETQ Ddd 6.5 )
  (SETQ Hh  3.6 )
))

 (IF (= DIM 8 )
(PROGN
  ( SETQ A 1.6 )
  (SETQ D  16 )
  (SETQ C 0.4  )
  (SETQ B 1.8  )
  (SETQ H 4.4  )
  (SETQ S 30 )
  (SETQ P 1.25 )
  (SETQ Dd 18 )
  (SETQ Ddd 8.8 )
  (SETQ Hh  4.6 )
))

(SETQ PLENGTH (DISTANCE P1 P2 ))
(SETQ L1  (- ( + (*  1.5  (/ D 2.0 )       ) PLENGTH ) (/ (- Dd D)  2.0) )  )
;(SETQ L    ( + (*  1.5  (/ D 2.0 )       ) PLENGTH )                      )
;(SETQ A (GETREAL"\n ENTER THE  A VALUE :"))
(SETQ L11  (- L1 H   )       )
 ( IF ( >= L1   S )
   (PROGN
       (SETQ AG1 (ANGLE P1 P2 ))
       (SETQ AG2 (* PI 0.5))
       ;;;;;;;;;;;;;;;;;;;;;;;;;;;;;;;;;;;;;;;;;;;;;;;;;;;;;;;;;;;;;CNT LAYER
       (SETQ PC    (POLAR P1  AG1  (/ (- Dd D ) 2.0 )))
       (SETQ pp1  (POLAR PC (- AG1 AG2) (/ A  2.0)    ))
       (SETQ DR1 (POLAR PC (- AG1 AG2) (/ D 2.0)      ))
       (SETQ C1   (POLAR PP1  AG1     C            ))
       (SETQ B1   (POLAR PP1    AG1          B     ))
       (SETQ DR2 (POLAR C1  (- AG1 AG2 ) (-  (/ (- D  a ) 2.0 ) C  )))
       (SETQ PP4 (POLAR PC   AG1  B         ))
       (SETQ PP3 (POLAR PC   AG1        H       ))
       (SETQ DR3 (POLAR PP3 (- AG1 AG2) (-  (/ D 2.0) H ) ))
       (SETQ pp11  (POLAR PC (+ AG1 AG2) (/ A  2.0)    ))
       (SETQ DR11 (POLAR PC (+ AG1 AG2) (/ D 2.0)      ))
       (SETQ C11  (POLAR PP11 AG1     C            ))
       (SETQ B11  (POLAR PP11   AG1          B     ))
       (SETQ DR22 (POLAR C11  (+ AG1 AG2 ) (-  (/ (- D a ) 2.0 ) C  )))
       (SETQ DR33  (POLAR PP3 (+ AG1 AG2) (-  (/ D 2.0) H ) ))
       (SETQ DR6  (POLAR DR3 AG1     (- L1 H   )  ))
       (SETQ DR66 (POLAR DR6 (+ AG1 AG2)(-    D (* H 2 )  ) ))
       (SETQ DR7  (POLAR DR6 (+ AG1 AG2)(/ (-    D (* H 2 )  ) 2 )  ))
       (SETQ PQ  (*  0.6495 P))
       (SETQ Q1   (POLAR DR6 (+ AG1 AG2)  PQ      ))
       (SETQ Q2   (POLAR DR6 (+ AG1 PI )  PQ      ))
       (SETQ Q3   (POLAR Q1  (+ AG1 PI )  S       ))
       (SETQ Q4   (POLAR DR6 (+ AG1 PI )  (+ S PQ      )    ))
       (SETQ Q11  (POLAR DR66 (- AG1 AG2)  PQ                ))
       (SETQ Q22  (POLAR DR66 (+ AG1 PI )  PQ               ) )
       (SETQ Q33  (POLAR Q11  (+ AG1 PI )  S                 ))
       (SETQ Q44  (POLAR DR66 (+ AG1 PI )(+ S PQ           ) ))

       ;;;;;;;;;;;;;;;;;;;;;;;;;;;;;;;;;;;;;;;;;;;;;;;;;;;;;;;;;;;;;HID LAYER
       (SETQ X1  (POLAR P1   (- AG1 AG2) (/  Dd  2.0)))
       (SETQ X2  (POLAR P1  (+ AG1 AG2) (/  Dd  2.0)))
       (SETQ PH (POLAR P1   AG1  Hh  ))
       (SETQ DLENGTH (DISTANCE P2 PH )        )
       (SETQ PH1 (POLAR PH  (+ AG1 AG2 ) (/ Ddd 2.0 )   ))
       (SETQ PH2 (POLAR PH  (- AG1 AG2 ) (/ Ddd 2.0 )   ))
       (SETQ PH22 (POLAR PH2  AG1     DLENGTH   ))
       (SETQ PH11 (POLAR PH1  AG1    DLENGTH         ))
       (SETQ PH111 (POLAR PH11 (+ AG1 AG2 )      5           ))
       (SETQ PH222 (POLAR PH22 ( - AG1 AG2 )     5         ))
       (SETQ QS1   (POLAR Q1   AG1    (* 0.125 D)       ))
       (SETQ QS11 (POLAR Q11  AG1    (* 0.125 D)       ))
       (SETQ PLENGTH3 (* 1.0 P                            ))
       (SETQ QS2  (POLAR QS1  AG1    PLENGTH3        ))
       (SETQ QS22  (POLAR QS11  AG1  PLENGTH3          ))
       ;;;;;;;;;;;;;;;;;;;;;;;;;;;;;;;;;;;;;;;;;;;;;;;;;CNT LINE
       (COMMAND "LAYER" "S" STOP2CNT  "")
       (COMMAND "LINE" DR3 Q2  Q1 Q11 Q22 Q44 DR33                                  "")
       (COMMAND "LINE" Q44 Q33 Q11  "")
       (COMMAND "LINE" Q4 Q3 Q1 "")
       (COMMAND "LINE" Q2 Q22  "")
       (COMMAND "LINE" Q33 Q3  "")
       (COMMAND "LINE" PP1 DR1 DR2 DR3 DR33 DR22 DR11 PP11 B11 B1 PP1               "")
       (COMMAND "LINE" DR22  C11   "")
       (COMMAND "LINE" DR2   C1    "")
      (SETQ K7    (POLAR QS2  (+ AG1 (/ PI 3 )) 1 ))
      (SETQ K8    (POLAR QS22 (- AG1 (/ PI 3 )) 1 ))
      (SETQ K9    (INTERS QS2 K7 QS22 K8 NIL ))
(SETQ  U1   (POLAR q2   AG1    (* 0.125 D)       ))
(SETQ  f1   (POLAR q22  AG1    (* 0.125 D)       ))
       ;;;;;;;;;;;;;;;;;;;;;;;;;;;;;;;;;;;;;;;;;;;;;;;;HID LINE
       (COMMAND "LAYER" "S" STOP2HID  "")
       (COMMAND "LINE" PH1 PH11    "" )
       (COMMAND "LINE" PH2  PH22   "" )
       ;(COMMAND "LINE" PH22  PH222   "" )
       ;(COMMAND "LINE" PH11  PH111  "" )
       (COMMAND "LINE" DR1  X1         "" )
       (COMMAND "LINE" Q1 QS1 QS11 Q11 "" )
       (COMMAND "LINE" QS1 QS2 QS22 QS11 "" )
       (COMMAND "LINE"         X2 DR11 "" )
       (COMMAND "LINE" QS2 K9 QS22    "" )
(COMMAND "LINE" q2   U1"")
(COMMAND "LINE" f1    q22  "")
(COMMAND "LINE" qs11  f1   "")
(COMMAND "LINE" qs1   u1   "")
       ;;;;;;;;;;;;;;;;;;;;;;;;;;;;;;;;;;;;;;;;;;;;;;;;;CEN LAYER LINE
       (COMMAND "LAYER" "S" STOP2CEN  "")
       (SETQ PX1  (POLAR P1   ( + AG1 PI )   0.5 ))
       (SETQ PX2  (POLAR K9      AG1        0.5  ))
       (COMMAND "LINE" PX1 PX2  "")
       (COMMAND "LAYER" "S" NLY "")
       ;;;;;;;;;;;;;;;;;;;;;;;;;;;;;;;;;;;;;;;;;;;;;;;;;;;;;;;NOT CAN
   )
)
;;;;;;;;;;;;;;;;;;;;;;;;;;;;;;;;;;SHORTER
(IF ( < L11 S  )
(PROGN
(SETQ AG1 (ANGLE P1 P2 ))
(SETQ AG2 (* PI 0.5))
;;;;;;;;;;;;;;;;;;;;;;;;;;;;;;;;;;;;;;;;;;;;;;;;;;;;;;;;;;;;;CNT LAYER
(SETQ PC    (POLAR P1  AG1  (/ (- Dd D ) 2.0 )))
(SETQ pp1  (POLAR PC (- AG1 AG2) (/ A  2.0)    ))
(SETQ DR1 (POLAR PC (- AG1 AG2) (/ D 2.0)      ))
(SETQ C1   (POLAR PP1  AG1     C            ))
(SETQ B1   (POLAR PP1    AG1          B     ))
(SETQ DR2 (POLAR C1  (- AG1 AG2 ) (-  (/ (- D  a ) 2.0 ) C  )))
(SETQ PP4 (POLAR PC   AG1  B         ))
(SETQ PP3 (POLAR PC   AG1        H       ))
(SETQ DR3 (POLAR PP3 (- AG1 AG2) (-  (/ D 2.0) H ) ))
(SETQ pp11  (POLAR PC (+ AG1 AG2) (/ A  2.0)    ))
(SETQ DR11 (POLAR PC (+ AG1 AG2) (/ D 2.0)      ))
(SETQ C11  (POLAR PP11 AG1     C            ))
(SETQ B11  (POLAR PP11   AG1          B     ))
(SETQ DR22 (POLAR C11  (+ AG1 AG2 ) (-  (/ (- D a ) 2.0 ) C  )))
(SETQ DR33  (POLAR PP3 (+ AG1 AG2) (-  (/ D 2.0) H ) ))
(SETQ DR6  (POLAR DR3 AG1     (- L1 H   )  ))
(SETQ DR66 (POLAR DR6 (+ AG1 AG2)(-    D (* H 2 )  ) ))
(SETQ DR7  (POLAR DR6 (+ AG1 AG2)(/ (-    D (* H 2 )  ) 2 )  ))
(SETQ PQ  (*  0.6495 P))
(SETQ Q1   (POLAR DR6 (+ AG1 AG2)  PQ      ))
(SETQ Q2   (POLAR DR6 (+ AG1 PI )  PQ      ))
(SETQ Q3   (POLAR Q1  (+ AG1 PI )  L11      ))
(SETQ Q11  (POLAR DR66 (- AG1 AG2)  PQ                ))
(SETQ Q22  (POLAR DR66 (+ AG1 PI )  PQ               ) )
(SETQ Q33  (POLAR Q11  (+ AG1 PI )  L11                ))
;;;;;;;;;;;;;;;;;;;;;;;;;;;;;;;;;;;;;;;;;;;;;;;;;;;;;;;;;;;;;HID LAYER
;(SETQ PX  (POLAR PC  (+ AG1 PI ) (/  (- Dd D ) 2.0)))
(SETQ X1  (POLAR P1   (- AG1 AG2) (/  Dd  2.0)))
(SETQ X2  (POLAR P1  (+ AG1 AG2) (/  Dd  2.0)))
(SETQ PH (POLAR P1   AG1  Hh  ))
(SETQ DLENGTH (DISTANCE P2 PH )        )
(SETQ PH1 (POLAR PH  (+ AG1 AG2 ) (/ Ddd 2.0 )   ))
(SETQ PH2 (POLAR PH  (- AG1 AG2 ) (/ Ddd 2.0 )   ))
(SETQ PH22 (POLAR PH2  AG1     DLENGTH   ))
(SETQ PH11 (POLAR PH1  AG1    DLENGTH         ))
(SETQ PH111 (POLAR PH11 (+ AG1 AG2 )      5           ))
(SETQ PH222 (POLAR PH22 ( - AG1 AG2 )     5         ))
(SETQ QS1   (POLAR Q1   AG1    (* 0.125 D)       ))
(SETQ QS11 (POLAR Q11  AG1    (* 0.125 D)       ))
(SETQ PLENGTH3 (* 1.0 P                            ))
(SETQ QS2  (POLAR QS1  AG1    PLENGTH3        ))
(SETQ QS22  (POLAR QS11  AG1  PLENGTH3          ))
(SETQ K7    (POLAR QS2  (+ AG1 (/ PI 3 )) 1 ))
(SETQ K8    (POLAR QS22 (- AG1 (/ PI 3 )) 1 ))
(SETQ K9    (INTERS QS2 K7 QS22 K8 NIL ))
(SETQ  U1   (POLAR q2   AG1    (* 0.125 D)       ))
(SETQ  f1   (POLAR q22  AG1    (* 0.125 D)       ))
;;;;;;;;;;;;;;;;;;;;;;;;;;;;;;;;;;;;;;;;;;;;;;;;;CNT LINE
(COMMAND "LAYER" "S" STOP2CNT  "")
(COMMAND "LINE" DR3 Q2  Q1 Q11 Q22     DR33  "")
(COMMAND "LINE"  Q33 Q11  "")
(COMMAND "LINE"  Q3 Q1 "")
(COMMAND "LINE" Q2 Q22  "")
(COMMAND "LINE" PP1 DR1 DR2 DR3 DR33 DR22 DR11 PP11 B11 B1 PP1   "")
(COMMAND "LINE" DR22  C11  "")
(COMMAND "LINE" DR2   C1   "")
;;;;;;;;;;;;;;;;;;;;;;;;;;;;;;;;;;;;;;;;;;;;;;;;HID LINE
(COMMAND "LAYER" "S" STOP2HID  "")
(COMMAND "LINE" PH1 PH11    "" )
(COMMAND "LINE" PH2  PH22   "" )
(COMMAND "LINE" DR1  X1         "" )
(COMMAND "LINE" Q1 QS1 QS11 Q11 "" )
(COMMAND "LINE" QS1 QS2 QS22 QS11 "" )
(COMMAND "LINE" DR11 X2         "" )
(COMMAND "LINE" QS2 K9 QS22    "" )
(COMMAND "LINE" q2  U1"")
(COMMAND "LINE" q22 f1   "")
(COMMAND "LINE" qs11  f1   "")
(COMMAND "LINE" qs1   u1   "")
;;;;;;;;;;;;;;;;;;;;;;;;;;;;;;;;;;;;;;;;;;;;;;;;;CEN LAYER LINE
(COMMAND "LAYER" "S" STOP2CEN  "")
(SETQ PX1  (POLAR P1   ( + AG1 PI )   1.0 ))
(SETQ PX2  (POLAR K9      AG1        1.0  ))
(COMMAND "LINE" PX1 PX2  "")
(COMMAND "LAYER" "S" NLY "")
 )    )
 )

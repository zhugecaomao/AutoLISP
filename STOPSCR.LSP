(defun mst ()
;(IF (= (TYPE F1) 'FILE ) "YES"  (STOP))
;(IF (= (TYPE F2) 'FILE ) "YES" (STOP))
  (setq sz (getint "\n Enter size [16] [18] [22] [26] [34]:"))
  (setq th (getreal "\n Enter thickness of fixed plate:"))
  (setq st (getreal "\n Enter stroke:"))
  (setq l (getreal "\n Enter screw length:"))
  (setq sl (getreal "\n Enter shoulder length:"))
  (setq a  (getreal "\n Enter angle:"))
  (setq bp (getpoint "\n Select insert point:"))
  (setq ang (* (/ a 180) pi))
  (if (= sz 16) (setq d1 10 d 22 h 8. k 1.5 s 30 dd 28))
  (if (= sz 18) (setq d1 13. d 24 h 10 k 2.0 s 35 dd 30))
  (if (= sz 22) (setq d1 16 d 28 h 12 k 2.0 s 40 dd 34))
  (if (= sz 26) (setq d1 20 d 30 h 14 k 2.5 s 45 dd 40))
  (if (= sz 34) (setq d1 25. d 42 h 18 k 2.5 s 50 dd 48))
  (if (or (< l s) (= l s)) (setq s l))
  (setq 1p (polar bp (+ ang 1.5709) (/ d 2)))
  (setq p1 (polar 1p (+ ang 3.1416) sl))
  (setq p2 (polar p1 (+ ang 3.1416) (- h 0.8)))
  (setq p3 (polar p2 (+ ang 4.1888) 1.6))
  (setq p4 (polar p3 (+ ang 4.7124) (- d 2.8)))
  (setq p5 (polar p4 (+ ang 5.236) 1.6))
  (setq p6 (polar p5 ang (- h 0.8)))
  (setq p7 (polar bp (+ ang 1.5709) (/ d1 2)))
  (setq p8 (polar p7 ang (- l k)))
  (setq p9 (polar p8 (+ ang 5.5) (* k 1.4)))
  (setq p10 (polar p9 (+ ang 4.7124) (- d1 (* k 2))))
  (setq p11 (polar p10 (+ ang 3.927) (* k 1.4)))
  (setq p12 (polar p11 (+ ang 3.1416) (- l k)))
  (setq p13 (polar p9 (+ ang 3.1416) s))
  (setq p14 (polar p9 ang 1))
  (setq p15 (polar p14 (+ ang 5.236) (* (- (/ d1 2) k) 1.155)))
  (setq p16 (polar p15 (+ ang 4.1888) (* (- (/ d1 2) k) 1.155)))
  (setq p17 (polar p16 (+ ang 3.1416) (+ s 1)))
  (setq p18 (polar p13 (+ ang 1.5709) k))
  (setq p19 (polar p17 (+ ang 4.7124) k))
  (setq p20 (polar bp (+ ang 1.5709) (/ sz 2)))
  (setq p21 (polar bp (+ ang 4.7124) (/ sz 2)))
  (setq p22 (polar p20 (+ ang 3.1416) sl))
  (setq p23 (polar p21 (+ ang 3.1416) sl))
  (setq p24 (polar p20 (+ ang 1.5709) 0.8))
  (setq p25 (polar p21 (+ ang 4.7124) 0.8))
  (setq p26 (polar p24 (+ ang 3.1416) (- sl st)))
  (setq p27 (polar p25 (+ ang 3.1416) (- sl st)))
  (setq p28 (polar p20 (+ ang 3.1416) (- sl st)))
  (setq p29 (polar p21 (+ ang 3.1416) (- sl st)))
  (setq p30 (polar p29 (+ ang 4.7124) (/ (- dd sz) 2)))
  (setq p31 (polar p28 (+ ang 1.5709) (/ (- dd sz) 2)))
  (setq p32 (polar p31 (+ ang 3.1416) (+ (- th sl) st)))
  (setq p33 (polar p30 (+ ang 3.1416) (+ (- th sl) st)))
  (command "line" p1 p2 p3 p4 p5 p6 p1 "")
  (command "line" p2 p5 "")
  (command "line" p7 p8 p9 p10 p11 p12 "")
  (command "line" p8 p11 "")
  (command "line" p13 p14 p15 p16 p17 "")
  (command "line" p18 p19 "")
  (command "line" p14 p16 "")
  (command "line" p20 p22 "")
  (command "line" p21 p23 "")
  (command "line" p24 p26 "")
  (command "line" p25 p27 "")
  (command "line" p28 p31 p32 "")
  (command "line" p29 p30 p33 "")
)

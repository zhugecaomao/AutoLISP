(defun c:TDB()
   (SETQ TH (GETVAR "TEXTSIZE"))
   (SETQ AG (GETVAR "LASTANGLE"))
   (SETQ UP (GETSTRING"\nUPPER:"))
   (SETQ DN (GETSTRING"\nDOWN:"))
   (SETQ IP (GETPOINT"\nInsert point:"))
   (PROMPT "\nText height<")(PRIN1 TH)(PROMPT ">:")
   (SETQ TH1 (GETREAL))
   (IF (= TH1 NIL)
       (SETQ TH1 TH)
   )
   (PROMPT "\nRotation angle:<")(PRIN1 AG)(PROMPT ">")
   (SETQ AG1 (GETREAL))
   (IF (= AG1 NIL)
       (SETQ AG1 AG)
   )
   (SETQ IP1 (POLAR IP (+ (DTR AG1) (DTR 90)) (+ TH1 (* TH1 0.2))))
   (COMMAND "TEXT" IP TH1 AG1 DN)
   (COMMAND "TEXT" IP1 TH1 AG1 UP)
)

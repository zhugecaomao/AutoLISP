(DEFUN C:TESTA4 ()
(SETQ S1 '(0 0) A (* 260 (GETVAR "DIMSCALE"))
B (* 195 (GETVAR "DIMSCALE")) S2 (APPEND (LIST A) (LIST 0))
S3 (APPEND (LIST A) (LIST B)) S4 (APPEND (LIST 0)(LIST B)))
(COMMAND "PLINE" S1 S2 S3 S4 "C")
(PRINC)
)

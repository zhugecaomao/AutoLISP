(defun c:THFE (/ ocm obl olderr pt ang opl)
  (setq	ocm	(getvar "cmdecho")
	obl	(getvar "blipmode")
	olderr	*ERROR*
	*error*	ai_abort
  )
  (setvar "cmdecho" 0)
  (setvar "blipmode" 0)
  (setvar "ltscale" 30)
  (initget 1)
  (setq pt (getpoint "\n指定点: "))
  (initget 0)
  (setq ang (getint "\n旋转角度<0>: "))
  (if (= ang nil)
    (setq ang 0)
  )
  (initget 0)
  (setq m (getint "\n吊環孔大小<24>:"))
  (if (= m nil)
    (setq m 24)
  )
  (command "insert" "c:/Autolisp/block/thfe.dwg" pt (/ m 24.00) "" ang)
  (setvar "cmdecho" ocm)
  (setvar "blipmode" obl)
  (setq *error* olderr)
  (princ)
)

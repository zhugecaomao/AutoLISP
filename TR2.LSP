(VMON)
;-----------------
;FILLET TWO LINES
(DEFUN C:TR2 (/ TC1 )
;(IF (= (TYPE F1) 'FILE ) "YES"  (STOP))
;(IF (= (TYPE F2) 'FILE ) "YES" (STOP))
(SETQ D1 (GETVAR "FILLETRAD"))
(SETQ TRDS D1)
(SETQ TRDS (RTOS TRDS 2 (GETVAR "LUPREC")))
(PROMPT "\nPlease Input Value Of Rad/<") (PROMPT TRDS)(PROMPT">:")
(setq D (getreal))
(IF (= D NIL)
    (setq D D1)
)
  (SETQ TC1 (ENTSEL "\nSelect First line:"))
  (SETQ TC2 (ENTSEL "\nSelect Second line:"))
  (setq a1 (ENTGET (car TC1)))
  (setq a2 (ENTGET (car TC2)))
  (SETQ ET1 (CDR (ASSOC 11 A1)))
  (SETQ ET2 (CDR (ASSOC 10 A1)))
  (SETQ ET3 (CDR (ASSOC 11 A2)))
  (SETQ ET4 (CDR (ASSOC 10 A2)))
  (SETVAR "FILLETRAD" D)
  (COMMAND "FILLET" TC1 TC2)
  (SETQ ER1 (LIST (/ (+ (CAR ET1) (CAR ET2)) 2) (/ (+ (CADR ET1) (CADR ET2)) 2)))
  (SETQ ER2 (LIST (/ (+ (CAR ET3) (CAR ET4)) 2) (/ (+ (CADR ET3) (CADR ET4)) 2)))
  (COMMAND "ERASE" ET1 ET2 ET3 ET4 "")
  (COMMAND "LINE" ET1 ET2 "")
  (COMMAND "LINE" ET3 ET4 "")
  (PRINC)
)

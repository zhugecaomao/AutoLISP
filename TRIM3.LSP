(DEFUN C:TRIM3()
(GC)
(SETQ CMD (GETVAR "CMDECHO"))
(SETVAR "CMDECHO" 0)
(SETQ OS (GETVAR "OSMODE"))
(setq name1 (entget (car (setq S1 (entsel "\nSelect First Line: ")))))
(setq name2 (entget (car (setq S2 (entsel "\nSelect Second Line: ")))))
(setvar "OSMODE" 0)
(SETQ E3 (SSGET)
        LE3 (SSLENGTH E3)
        NUM3 0)
 (setq pt1 (cdr (assoc 10 name1)))
 (setq pt2 (cdr (assoc 11 name1)))
 (setq pt3 (cdr (assoc 10 name2)))
 (setq pt4 (cdr (assoc 11 name2)))
(PROGN
  (REPEAT LE3
    (SETQ H (CDAR (SETQ K (ENTGET (SSNAME E3 NUM3))))
          K2 (CDR (ASSOC 10 K))
          K3 (CDR (ASSOC 11 K)))
    (SETQ PJ (INTERS K2 K3 PT1 PT2)
          PK (INTERS K2 K3 PT3 PT4))
    (COMMAND "BREAK" H PJ PK)
    (SETQ NUM3 (+ NUM3 1))
  )
 )
(SETVAR "CMDECHO" CMD)
)

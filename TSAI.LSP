(SETQ P (GETPOINT "\nSTART POINT"))
(SETQ L (GETREAL "\nLENGTH"))
(SETQ W (GETREAL "\nWIDTH"))
(SETQ D (GETREAL "\nDIST OF BETWEEN BOX"))
(SETQ N (GETINT "\nNUMBER"))
(SETQ PP P)
(SETQ P1  (POLAR P (DTR 90) W))
(SETQ P2  (POLAR P1 (DTR 0) L))
(SETQ P3  (POLAR P2 (DTR 270) W))
(COMMAND "LINE" P P1 P2 P3 "C")
(REPEAT N
 (SETQ PP (POLAR PP (DTR 90) (+ W D)))
 (COMMAND "COPY" "C" P P2 "" P PP)
)

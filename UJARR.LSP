(defun UJARR()
;(IF (= (TYPE F1) 'FILE ) "YES"  (STOP))
;(IF (= (TYPE F2) 'FILE ) "YES" (STOP))
(setq a (getvar "textsize"))
(prompt "last textsize is:")
(prin1 a)
(SETQ ANS (strcase (GETSTRING "\nDO YOU WANT TO CHANGE LAST SETTING <Y/N> N:")))
   (IF (= ANS "Y")
       (setq a (getreal "\ninput textsize:"))
       (setq a (getvar "textsize"))
   )
(COMMAND "SETVAR" "CMDECHO" "0")
  (repeat 5
     (setq n (getstring "\nEnter detail name: "))
     (setq p1 (getpoint "\nEnter center point: "))
;    (setq n1 (strcat "SECTION:" N ))
     (COMMAND "TEXT" P1 A 90 N)
     (setq CP1 (list (+ (car p1) (/ A 5)) (+ (cadr p1) (* A 0.9))))
     (setq CP2 (list (+ (car p1) (/ A 5)) (- (cadr p1) (* A 0.2))))
     (setq CP3 (list (+ (car p1) (/ A 5) (/ A 10)) (+ (cadr p1) (* A 0.9))))
     (setq CP4 (list (+ (car p1) (/ A 5) (/ A 10)) (- (cadr p1) (* A 0.2))))
     (SETQ MID1 (LIST (+ (CAR P1) (* A 0.6)) (/ (+ (CADR CP1) (CADR CP2)) 2)))
     (SETQ MID2 (LIST (+ (CAR MID1) 5) (CADR MID1)))
     (SETQ MID3 (POLAR MID1 0.1745 10))
     (SETQ MID4 (POLAR MID3 4.88692 3.92 ))
     (SETQ INT1 (INTERS MID1 MID2 MID3 MID4 NIL))
     (SETQ MID2 (LIST (+ (CAR INT1) 10) (CADR INT1)))
     (COMMAND "LINE" CP1 CP2 "")
     (COMMAND "LINE" CP3 CP4 "")
     (COMMAND "LINE" MID1 MID2 "")
     (COMMAND "LINE" MID1 MID3 "")
     (COMMAND "LINE" MID3 MID4 "")
     (PROMPT"\nDraging Cursor or Key Rotate Angle:")
     (COMMAND "ROTATE" "CROSSING" P1 MID2 "" P1 PAUSE)
  )
)

(defun UJARR1()
;(IF (= (TYPE F1) 'FILE ) "YES"  (STOP))
;(IF (= (TYPE F2) 'FILE ) "YES" (STOP))
(setq a (getvar "textsize"))
(prompt "last textsize is:")
(prin1 a)
(SETQ ANS (strcase (GETSTRING "\nDO YOU WANT TO CHANGE LAST SETTING <Y/N> N:")))
   (IF (= ANS "Y")
       (setq a (getreal "\ninput textsize:"))
       (setq a (getvar "textsize"))
   )
(COMMAND "SETVAR" "CMDECHO" "0")
  (repeat 5
     (setq n (getstring "\nEnter detail name: "))
     (setq p1 (getpoint "\nEnter center point: "))
;    (setq n1 (strcat "SECTION:" N ))
     (COMMAND "TEXT" P1 A 90 N)
     (setq CP1 (list (+ (car p1) (/ A 5)) (+ (cadr p1) (* A 1.1))))
     (setq CP2 (list (+ (car p1) (/ A 5)) (- (cadr p1) (* A 0.1))))
     (setq CP3 (list (+ (car p1) (/ A 5) (/ A 10)) (+ (cadr p1) (* A 1.1))))
     (setq CP4 (list (+ (car p1) (/ A 5) (/ A 10)) (- (cadr p1) (* A 0.1))))
     (SETQ MID1 (LIST (+ (CAR P1) (* A 0.6)) (/ (+ (CADR CP1) (CADR CP2)) 2)))
     (SETQ MID2 (LIST (+ (CAR MID1) 5) (CADR MID1)))
     (SETQ MID3 (POLAR MID1 0.1745 10))
     (SETQ MID4 (POLAR MID3 4.88692 3.92 ))
     (SETQ INT1 (INTERS MID1 MID2 MID3 MID4 NIL))
     (SETQ MID2 (LIST (+ (CAR INT1) 10) (CADR INT1)))
     (COMMAND "LINE" CP1 CP2 "")
     (COMMAND "LINE" CP3 CP4 "")
     (COMMAND "LINE" MID1 MID2 "")
     (COMMAND "LINE" MID1 MID3 "")
     (COMMAND "LINE" MID3 MID4 "")
     (PROMPT"\nDraging Cursor or Key Rotate Angle:")
     (COMMAND "ROTATE" "CROSSING" P1 MID2 "" P1 PAUSE)
  )
)

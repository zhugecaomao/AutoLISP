(DEFUN C:KOMM ()
(SETQ P1 (GETPOINT "\n INSERT POINT:"))
(SETQ TH (GETPOINT P1"\n THICKNESS POINT:"))
(SETQ H 3)
(MENUCMD "S=KO")
(SETQ D (GETREAL "\nDIM :"))
(SETQ AG1 (ANGLE P1 TH))
(SETQ AG2 (* PI 0.5))
(SETQ LSE (DISTANCE P1 TH))
(SETQ DR1 (POLAR (POLAR P1 AG1 H) (+ AG1 AG2) (/ D 2.0)))
(SETQ DR2 (POLAR (POLAR P1 AG1 H) (- AG1 AG2) (/ D 2.0)))
(SETQ DR3 (POLAR (POLAR P1 AG1 (- LSE H)) (+ AG1 AG2) (/ D 2.0)))
(SETQ DR4 (POLAR (POLAR P1 AG1 (- LSE H)) (- AG1 AG2) (/ D 2.0)))
(COMMAND "LINE" DR1 DR3 DR4 DR2 "C")
(COMMAND "LINE" DR1 (POLAR DR1 (+ AG1 (DTR 135)) 4.2427) "")
(COMMAND "LINE" DR2 (POLAR DR2 (- AG1 (DTR 135)) 4.2427) "")
(COMMAND "LINE" DR3 (POLAR DR3 (+ AG1 (DTR 45)) 4.2427) "")
(COMMAND "LINE" DR4 (POLAR DR4 (- AG1 (DTR 45)) 4.2427) "")
)

(DEFUN C:KOIN ()
(SETQ P1 (GETPOINT "\n INSERT POINT:"))
(SETQ TH (GETPOINT P1"\n THICKNESS POINT:"))
(SETQ H (/ 3 25.4))
(MENUCMD "S=KO")
(SETQ D (GETREAL "\nDIM :"))
(SETQ AG1 (ANGLE P1 TH))
(SETQ AG2 (* PI 0.5))
(SETQ LSE (DISTANCE P1 TH))
(SETQ DR1 (POLAR (POLAR P1 AG1 H) (+ AG1 AG2) (/ D 2.0)))
(SETQ DR2 (POLAR (POLAR P1 AG1 H) (- AG1 AG2) (/ D 2.0)))
(SETQ DR3 (POLAR (POLAR P1 AG1 (- LSE H)) (+ AG1 AG2) (/ D 2.0)))
(SETQ DR4 (POLAR (POLAR P1 AG1 (- LSE H)) (- AG1 AG2) (/ D 2.0)))
(COMMAND "LINE" DR1 DR3 DR4 DR2 "C")
(COMMAND "LINE" DR1 (POLAR DR1 (+ AG1 (DTR 135)) 0.167035) "")
(COMMAND "LINE" DR2 (POLAR DR2 (- AG1 (DTR 135)) 0.167035) "")
(COMMAND "LINE" DR3 (POLAR DR3 (+ AG1 (DTR 45)) 0.167035) "")
(COMMAND "LINE" DR4 (POLAR DR4 (- AG1 (DTR 45)) 0.167035) "")
)

(defun UJSEC()
;(IF (= (TYPE F1) 'FILE ) "YES"  (STOP))
;(IF (= (TYPE F2) 'FILE ) "YES" (STOP))
(COMMAND "SETVAR" "CMDECHO" "0")
(setq a (getvar "textsize"))
(prompt "last textsize is:")
(prin1 a)
(SETQ ANS (strcase (GETSTRING "\nDO YOU WANT TO CHANGE LAST SETTING <Y/N> N:")))
   (IF (= ANS "Y")
       (setq a (getreal "\ninput textsize:"))
       (setq a (getvar "textsize"))
   )
  (repeat 5
     (setq n (getstring "\nEnter detail name: "))
     (setq p1 (getpoint "\nEnter center point: "))
     (setq n1 (strcat "SECTION:" N ))
     (SETQ NUM (STRLEN N1))
     (COMMAND "TEXT" P1 A 0 N1)
     (setq CP1 (list (- (car p1) (/ A 10)) (- (cadr p1) (/ A 5))))
     (setq CP2 (list (+ (car p1) (* (- NUM 0.4767) A)) (- (cadr p1) (/ A 5))))
     (setq CP3 (list (- (car p1) (/ A 10)) (- (cadr p1) (/ A 5) 1)))
     (setq CP4 (list (+ (car p1) (* (- NUM 0.4767) A)) (- (cadr p1) (/ A 5) 1)))
     (COMMAND "LINE" CP1 CP2 "")
     (COMMAND "LINE" CP3 CP4 "")
     (PROMPT"\nDraging Cursor or Key Rotate Angle:")
     (COMMAND "ROTATE" "CROSSING" P1 (LIST (+ (CAR P1) A) (- (CADR P1) A)) "" P1 PAUSE)
  )
)

(defun UJSEC1()
;(IF (= (TYPE F1) 'FILE ) "YES"  (STOP))
;(IF (= (TYPE F2) 'FILE ) "YES" (STOP))
(COMMAND "SETVAR" "CMDECHO" "0")
(setq a (getvar "textsize"))
(prompt "last textsize is:")
(prin1 a)
(SETQ ANS (strcase (GETSTRING "\nDO YOU WANT TO CHANGE LAST SETTING <Y/N> N:")))
   (IF (= ANS "Y")
       (setq a (getreal "\ninput textsize:"))
       (setq a (getvar "textsize"))
   )
  (repeat 5
     (setq n (getstring "\nEnter detail name: "))
     (setq p1 (getpoint "\nEnter center point: "))
     (setq n1 (strcat "SECTION:" N ))
     (SETQ NUM (STRLEN N1))
     (COMMAND "TEXT" P1 A 0 N1)
     (setq CP1 (list (- (car p1) (/ A 10)) (- (cadr p1) (/ A 5))))
     (setq CP2 (list (+ (car p1) (* (- NUM 0.7567) A)) (- (cadr p1) (/ A 5))))
     (setq CP3 (list (- (car p1) (/ A 10)) (- (cadr p1) (/ A 5) 1)))
     (setq CP4 (list (+ (car p1) (* (- NUM 0.7567) A)) (- (cadr p1) (/ A 5) 1)))
     (COMMAND "LINE" CP1 CP2 "")
     (COMMAND "LINE" CP3 CP4 "")
     (PROMPT"\nDraging Cursor or Key Rotate Angle:")
     (COMMAND "ROTATE" "CROSSING" P1 (LIST (+ (CAR P1) A) (- (CADR P1) A)) "" P1 PAUSE)
  )
)

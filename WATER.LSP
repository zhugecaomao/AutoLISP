(DEFUN C:WATER ()
   (SETVAR "CMDECHO" 0)
   (SETQ VC (GETVAR "VIEWCTR"))
   (SETQ YR (GETVAR "VIEWSIZE"))
   (SETQ XR (* YR 1.3864))
   (SETQ YD (/ YR 12))
   (SETQ XD (/ XR 4))
   (SETQ XB (- (CAR VC) (/ XR 2)))
   (SETQ YB (- (CADR VC) (/ YR 2)))
   (COMMAND "VSLIDE" "C:/ACAD/SLIDE/WATER")
;----
   (SETQ PT (GETPOINT "\nPLEASE DIGIT THE CHAR. TABLE : "))
             (SETQ XP (CAR PT))
             (SETQ YP (CADR PT))
             (SETQ XAA (- XP XB))
             (SETQ YAA (- YP YB))
             (SETQ XA (ABS XAA))
             (SETQ YA (ABS YAA))
             (SETQ X (FIX ( / XA XD)))
             (SETQ Y (FIX ( / YA YD)))
;
      (IF (AND (= X 1) (= Y 0))
      (COMMAND "REDRAW" "INSERT" "C:/ACAD/BLOCK/W1-2MM-2" PAUSE 1 1))
      (IF (AND (= X 3) (= Y 0))
      (COMMAND "REDRAW" "INSERT" "C:/ACAD/BLOCK/W1-2IN-2" PAUSE 1 1))
      (IF (AND (= X 1) (= Y 1))
      (COMMAND "REDRAW" "INSERT" "C:/ACAD/BLOCK/W1-2MM-1" PAUSE 1 1))
      (IF (AND (= X 3) (= Y 1))
      (COMMAND "REDRAW" "INSERT" "C:/ACAD/BLOCK/W1-2IN-1" PAUSE 1 1))
      (IF (AND (= X 1) (= Y 2))
      (COMMAND "REDRAW" "INSERT" "C:/ACAD/BLOCK/W1-2MM" PAUSE 1 1))
      (IF (AND (= X 3) (= Y 2))
      (COMMAND "REDRAW" "INSERT" "C:/ACAD/BLOCK/W1-2IN" PAUSE 1 1))
      (IF (AND (= X 1) (= Y 3))
      (COMMAND "REDRAW" "INSERT" "C:/ACAD/BLOCK/W3-8MM-2" PAUSE 1 1))
      (IF (AND (= X 3) (= Y 3))
      (COMMAND "REDRAW" "INSERT" "C:/ACAD/BLOCK/W3-8IN-2" PAUSE 1 1))
      (IF (AND (= X 1) (= Y 4))
      (COMMAND "REDRAW" "INSERT" "C:/ACAD/BLOCK/W3-8MM-1" PAUSE 1 1))
      (IF (AND (= X 3) (= Y 4))
      (COMMAND "REDRAW" "INSERT" "C:/ACAD/BLOCK/W3-8IN-1" PAUSE 1 1))
      (IF (AND (= X 1) (= Y 5))
      (COMMAND "REDRAW" "INSERT" "C:/ACAD/BLOCK/W3-8MM" PAUSE 1 1))
      (IF (AND (= X 3) (= Y 5))
      (COMMAND "REDRAW" "INSERT" "C:/ACAD/BLOCK/W3-8IN" PAUSE 1 1))
      (IF (AND (= X 1) (= Y 6))
      (COMMAND "REDRAW" "INSERT" "C:/ACAD/BLOCK/W1-4MM-2" PAUSE 1 1))
      (IF (AND (= X 3) (= Y 6))
      (COMMAND "REDRAW" "INSERT" "C:/ACAD/BLOCK/W1-4IN-2" PAUSE 1 1))
      (IF (AND (= X 1) (= Y 7))
      (COMMAND "REDRAW" "INSERT" "C:/ACAD/BLOCK/W1-4MM-1" PAUSE 1 1))
      (IF (AND (= X 3) (= Y 7))
      (COMMAND "REDRAW" "INSERT" "C:/ACAD/BLOCK/W1-4IN-1" PAUSE 1 1))
      (IF (AND (= X 1) (= Y 8))
      (COMMAND "REDRAW" "INSERT" "C:/ACAD/BLOCK/W1-4MM" PAUSE 1 1))
      (IF (AND (= X 3) (= Y 8))
      (COMMAND "REDRAW" "INSERT" "C:/ACAD/BLOCK/W1-4IN" PAUSE 1 1))
      (IF (AND (= X 1) (= Y 9))
      (COMMAND "REDRAW" "INSERT" "C:/ACAD/BLOCK/W1-8MM-2" PAUSE 1 1))
      (IF (AND (= X 3) (= Y 9))
      (COMMAND "REDRAW" "INSERT" "C:/ACAD/BLOCK/W1-8IN-2" PAUSE 1 1))
      (IF (AND (= X 1) (= Y 10))
      (COMMAND "REDRAW" "INSERT" "C:/ACAD/BLOCK/W1-8MM-1" PAUSE 1 1))
      (IF (AND (= X 3) (= Y 10))
      (COMMAND "REDRAW" "INSERT" "C:/ACAD/BLOCK/W1-8IN-1" PAUSE 1 1))
      (IF (AND (= X 1) (= Y 11))
      (COMMAND "REDRAW" "INSERT" "C:/ACAD/BLOCK/W1-8MM" PAUSE 1 1))
      (IF (AND (= X 3) (= Y 11))
      (COMMAND "REDRAW" "INSERT" "C:/ACAD/BLOCK/W1-8IN" PAUSE 1 1))
      )

;1990/01/22 PM:
 (defun c:zpa ()

;(IF (= (TYPE F1) 'FILE ) "YES"  (STOP))
;(IF (= (TYPE F2) 'FILE ) "YES" (STOP))
 (defun setup()
   (setq ch (getstring "\n,D(6)(8)(10)(12) ?"))

   (setq l (getreal "\n How about the ZPA longer ?"))

   (setq base (getpoint "\n Where will you put on the ZPA ?"))
   (setq x1 (eval (car base)))
   (setq y1 (eval (cadr base)))

   (setvar "cmdecho" 1)
   (while (or (eq ch "6") (eq ch "D6")) (D6))
   (while (or (eq ch "8") (eq ch "D8")) (D8))
   (while (or (eq ch "10") (eq ch "D10")) (D10))
   (while (or (eq ch "12") (eq ch "D12")) (D12))
 )

 (defun D6()
   (setq b 10)
   (setq d 6.0)
   (setq h 6)
   (setup1)
 )

 (defun D8()
   (setq b 13)
   (setq d 8.0)
   (setq h 8)
   (setup1)
 )

 (defun D10()
   (setq b 15)
   (setq d 10.0)
   (setq h 8)
   (setup1)
 )

 (defun D12()
   (setq b 17)
   (setq d 12.0)
   (setq h 8)
   (setup1)
 )

 (defun setup1()
   (setq b1 (/ b 2))
   (setq d1 (/ d 2))
   (if (< l 0) (setq h (* -1 h)))
   (setq p1 (list (- x1 b1) y1))
   (setq p2 (list (+ x1 b1) y1))
   (setq p3 (list (+ x1 b1) (+ y1 h)))
   (setq p4 (list (- x1 b1) (+ y1 h)))
   (command "pline" p1 "w" "0" "0" p2 p3 p4 p1 "")

   (setq p5 (list (+ x1 d1) (+ y1 h)))
   (setq p6 (list (+ x1 d1) (+ y1 l)))
   (setq p7 (list x1 (+ y1 l)))
   (setq p8 (list (+ x1 1) (- (+ y1 l) 3)))
   (setq p9 (list (- x1 d1) (- (+ y1 l) 3)))
   (setq p10 (list (- x1 d1) (+ y1 h)))
   (command "pline" p5 "w" "0" "0" p6 P7 P8 P9 p10 "")
   (setup)
 )
   (setup)
 )

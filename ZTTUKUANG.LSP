(DEFUN C:ZTTUKUANG ()
;  (SETQ TEST 1)
   (SETVAR "CMDECHO" 0)
   (SETQ VC (GETVAR "VIEWCTR"))
   (SETQ YR (GETVAR "VIEWSIZE"))
   (SETQ XR (* YR 1.4833))
   (SETQ YD (/ YR 6))
   (SETQ XD (/ XR 6))
   (SETQ XB (- (CAR VC) (/ XR 2)))
   (SETQ YB (- (CADR VC) (/ YR 2)))
   (COMMAND "VSLIDE" "C:/ACAD/SLIDE/ZTTUKUANG")
;--------------------------------------------------------------------
    (SETQ PT (GETPOINT "\nPLEASE DIGIT THE CHAR. TABLE : "))
             (SETQ XP (CAR PT))
             (SETQ YP (CADR PT))
             (SETQ XAA (- XP XB))
             (SETQ YAA (- YP YB))
             (SETQ XA (ABS XAA))
             (SETQ YA (ABS YAA))
             (SETQ X (FIX ( / XA XD)))
             (SETQ Y (FIX ( / YA YD)))
;
      (IF (AND (= X 0) (= Y 5))
      (COMMAND "REDRAW" "INSERT" "C:/ACAD/BLOCK/ZTA0" PAUSE 1 1 0))
      (IF (AND (= X 1) (= Y 5))
      (COMMAND "REDRAW" "INSERT" "C:/ACAD/BLOCK/ZTA1" PAUSE 1 1 0))
      (IF (AND (= X 2) (= Y 5))
      (COMMAND "REDRAW" "INSERT" "C:/ACAD/BLOCK/ZTA2" PAUSE 1 1 0))
      (IF (AND (= X 3) (= Y 5))
      (COMMAND "REDRAW" "INSERT" "C:/ACAD/BLOCK/ZTA3" PAUSE 1 1 0))
      (IF (AND (= X 4) (= Y 5))
      (COMMAND "REDRAW" "INSERT" "C:/ACAD/BLOCK/ZTA4" PAUSE 1 1 0))
      (IF (AND (= X 5) (= Y 5))
      (COMMAND "REDRAW" "INSERT" "C:/ACAD/BLOCK/ZTTITLE01" PAUSE 1 1 0))
      (IF (AND (= X 0) (= Y 4))
      (COMMAND "REDRAW" "INSERT" "C:/ACAD/BLOCK/ZTTITLE02" PAUSE 1 1 0))
      (IF (AND (= X 1) (= Y 4))
      (COMMAND "REDRAW" "INSERT" "C:/ACAD/BLOCK/ZTCIBOM" PAUSE 1 1 0))
      (IF (AND (= X 2) (= Y 4))
      (COMMAND "REDRAW" "INSERT" "C:/ACAD/BLOCK/ZTDCIBOM" PAUSE 1 1 0))
      (IF (AND (= X 3) (= Y 4))
      (COMMAND "REDRAW" "INSERT" "C:/ACAD/BLOCK/" PAUSE 1 1 0))
      (IF (AND (= X 4) (= Y 4))
      (COMMAND "REDRAW" "INSERT" "C:/ACAD/BLOCK/" PAUSE 1 1 0))
      (IF (AND (= X 5) (= Y 4))
      (COMMAND "REDRAW" "INSERT" "C:/ACAD/BLOCK/ZTDINGLIAO" PAUSE 1 1 0))
     )

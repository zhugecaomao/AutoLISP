;**********************************************************************
(defun c:zb()
    (setq  p (getpoint "\n Point:"))
    (setq x (car p) y (cadr p))
    (setq p1 (getpoint "\n Point:")
          p2 (getpoint "\n Point:"))
    (SETQ Y1 (CADR P1))
    (setq x1 (car p1))
    (setq x2 (car p2) y2 (cadr p2))
    (if (< x2 (car p1)) (setq x2 (- x1 400))
                         (setq x2 (+ x1 400)))
    (setq p2 (list x2 y1 ))
    (command "line" p p1 p2 "")
    (if (> x2 x1) (setq x2 x1)
                  (setq x2 (- x2 0.1)))
    (setq p3 (list x2 (+ y1 25.0))
          p4 (list x2 (- y1 75.0)))
    (setq x0 (rtos x 2 3)
          y0 (rtos y 2 3))
    (setq xx (strcat "Y" x0)
          YY (STRCAT "X" y0))
    (COMMAND "TEXT" P3 45 0 YY)
    (COMMAND "TEXT" P4 45 0 XX)
;    (COMMAND "TEXT" P3 45 90 YY)
;    (COMMAND "TEXT" P4 45 90 XX)
    (princ)
)
 ;**********************************************************************

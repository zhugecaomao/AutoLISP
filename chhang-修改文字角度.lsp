;批量修改文字角度程序
(DEFUN C:chhang ()
 (princ "\nselect object:")
 (setq s (ssget))
 (setq hig (getreal "\n输入角度<0>:"))
 (if (= hig nil) (setq hig 0.0))
 (setq hig (* pi hig) hig (/ hig 180.0))
 (setq h50 (cons 50 hig))
 (setq n (sslength s))
 (setq k 0 )
 (while (< k n) 
      (setq name (ssname s k))
      (setq a (entget name))
      (setq b (assoc '0 a))
      (setq b (cdr b))
      (if (= b "TEXT")(progn
        (setq h (assoc '50 a))
        (setq a (subst h50 h a))
        (entmod a)
        ))
      (setq k (+ k 1))
 )
)

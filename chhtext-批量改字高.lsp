(DEFUN C:CHHTEXT ()
 (princ "\nselect object:")
 (setq s (ssget))
 (setq hig (getreal "\n输入新字高<3>:"))
 (if (= hig nil) (setq hig 3.0))
 (setq h40 (cons 40 hig))
 (setq n (sslength s))
 (setq k 0 )
 (while (< k n) 
      (setq name (ssname s k))
      (setq a (entget name))
      (setq b (assoc '0 a))
      (setq b (cdr b))
      (if (= b "TEXT")(progn
        (setq h (assoc '40 a))
        (setq a (subst h40 h a))
        (entmod a)
        ))
      (setq k (+ k 1))
 )
)

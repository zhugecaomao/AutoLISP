;除法计算
(DEFUN C:chu1()
 (setq jd (getint "input 精度<0>:"))
 (if (= jd nil) (setq jd 0))
 (princ "\nselect object:")
 (setq s (ssget))
 (setq n (sslength s))
 (setq k 0 )(setq mm 0.0)
 (while (< k n) 
      (setq name (ssname s k))
      (setq a (entget name))
      (setq t1 (assoc '0 a))
      (setq t1 (cdr t1))
      (if (= t1 "TEXT") (PROGN
          (setq tx (assoc '1 a))
          (setq tx (cdr tx))
          (setq tx (atof tx))
          (if (= k 0) (setq MM TX))
          (if (/= k 0) (setq mm (/ mm tx)))
         ))
      (if (= t1 "DIMENSION") (PROGN
          (setq tx (assoc '1 a))
          (setq tx (cdr tx))
          (if (and (/= tx "")(/= tx "<>"))(setq tx (atof tx)))
          (if (or (= tx "")(= tx "<>"))(progn
              (setq tx (assoc '42 a))
              (setq tx (cdr tx))
;              (setq tx (+ tx 0.5))
;              (setq tx (fix tx))
              ))
          (if (= k 0) (setq MM TX))
          (if (/= k 0) (setq mm (/ mm tx)))
         ))
      (setq k (+ k 1))
 )
 (setq mm (rtos mm 2 jd))
 (setq po (getpoint "input point----:"))
 (command "text" po ""  "" mm)
)

(defun c:mm (/ var la ocm obl olderr )
  (setq ocm (getvar "cmdecho") 
        obl (getvar "blipmode")
        olderr *ERROR*
        *error* ai_abort) 
  (setvar "cmdecho" 0) (setvar "blipmode" 0)
  (setq ss (ssget))
  (setq p1 (getpoint "select the base point:"))
  (setq p2 '(0 0))
  (command "move" ss "" p1 p2)
  (command "zoom" "e")
  (command "regen")
  (setvar "cmdecho" ocm) (setvar "blipmode" obl)
  (setq *error* olderr)
  (princ)
)

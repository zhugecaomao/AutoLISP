;;亮显指定颜色的实体
(defun c:testa (/ coa co ssco i one )
  (setq coa (getvar "CECOLOR"))
  (initdia)
  (command ".color")(setvar "cmdecho" 0)
  (setq co (getvar "CECOLOR"))
  (SETQ SSCO(SSGET "X" (LIST (CONS 62 (atoi co)))))
  (setvar "CECOLOR" coa)
  (setq i 0)
  (repeat (sslength ssco)
    (setq one (ssname ssco i))
    (redraw one 3)
    (setq i (1+ i)))
  (setvar "cmdecho" 1) (princ))

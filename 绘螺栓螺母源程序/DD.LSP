(defun dtr(a)
  (* a (/ pi 180.0))
)
(defun C:dd()
 (setq o(getpoint "\n 输入插入点:"))
 (setq d0(getreal "\n 输入弹垫规格:"))
 (SETQ SC(GETREAL "\n 输入比例系数:"))
 (setq ang1(getangle o "\n 输入旋转角度:"))
 (setq ang(- (/ (* ang1 180) pi) 90))
 (setq os(getvar "osmode"))
 (command "osmode" 0)
 (cond ((= d0 5) (setq d1 5.1) (setq b0 1.3) (setq m0 0.65))
       ((= D0 6) (setq d1 6.1) (setq b0 1.6) (setq m0 0.8))
       ((= D0 8) (setq d1 8.1) (setq b0 2.1) (setq m0 1.05))
       ((= D0 10) (setq d1 10.2) (setq b0 2.6) (setq m0 1.3))
       ((= D0 12) (setq d1 12.2) (setq b0 3.1) (setq m0 1.55))
       ((= D0 16) (setq d1 16.2) (setq b0 4.1) (setq m0 2.05))
       ((= D0 20) (setq d1 20.2) (setq b0 5.0) (setq m0 2.5))
       ((= D0 24) (setq d1 24.5) (setq b0 6.0) (setq m0 3.0))
       ((= D0 30) (setq d1 30.5) (setq b0 7.5) (setq m0 3.75))
       ((= D0 36) (setq d1 36.5) (setq b0 9.0) (setq m0 4.5))
       ((= D0 42) (setq d1 42.5) (setq b0 10.5) (setq m0 5.25))
       ((= D0 48) (setq d1 48.5) (setq b0 12.0) (setq m0 6.0))
)
  (SETQ D(* d1 sc))
  (setq b(* b0 sc))
  (setq m(* m0 sc))
  (setq c(cos (dtr 15))) 
  (setq t(/ (sin (dtr 15)) c))
  (setq p1(list (- 0 (/ (+ b d) 2)) 0))
  (setq p2(list (/ (+ b d) 2) 0))
  (command "ucs" "o" o)
  (command "ucs" "z" ang)
  (command "line" p1 p2 "") 
  (setq p3(list (- 0 (/ (+ b d) 2)) b))
  (setq p4(list (/ (+ b d) 2) b))
  (command "line" p3 p4 "")
  (command "line" p4 p2 "")
  (COMMAND "LINE" P3 P1 "")
  (SETQ P5 (LIST (/ M (* 2 C)) 0))
  (SETQ p6 (LIST (- (/ M (* C 2)) (* T B)) B))
  (command "line" p5 p6 "")
  (setq p7 (list (- 0 (/ m (* 2 c))) 0))
  (setq p8 (list (- 0 (+ (/ m (* 2 c)) (* b t))) b))
  (command "line" p7 p8 "")
  (command "ucs" "z" (- 0 ang))
  (command "ucs" "w")
  (command "osmode" os)
  (COMMAND "REDRAWALL")
  (princ)
)

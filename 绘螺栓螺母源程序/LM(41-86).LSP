(defun C:LM()
 (setq o(getpoint "\n 输入插入点:"))
 (setq d0(getreal "\n 输入螺母规格:"))
 (SETQ SC(GETREAL "\n 输入比例系数:"))
 (setq ang1(getangle o "\n 输入旋转角度:"))
 (setq ang(- (/ (* ang1 180) pi) 90))
 (setq os(getvar "osmode"))
 (command "osmode" 0)
 (cond ((= d0 5) (setq e0 8.63) (setq m0 5.6))
       ((= D0 6) (setq E0 11.0) (setq m0 6.1))
       ((= D0 8) (setq E0 14.4) (setq m0 7.9))
       ((= D0 10) (setq E0 17.8) (setq m0 9.5))
       ((= D0 12) (setq E0 20.0) (setq m0 12.2))
       ((= D0 14) (setq E0 23.4) (setq m0 13.9))
       ((= D0 16) (setq E0 26.8) (setq m0 14.9))
       ((= D0 18) (setq E0 29.6) (setq m0 15.9))
       ((= D0 20) (setq E0 33.0) (setq m0 18.7))
       ((= D0 24) (setq E0 39.6) (setq m0 22.3))
       ((= D0 30) (setq E0 50.9) (setq m0 26.4))
       ((= D0 36) (setq E0 60.8) (setq m0 31.5))
       ((= D0 42) (setq E0 72) (setq m0 34.9))
       ((= D0 48) (setq E0 82.6) (setq m0 38.9))
       ((= D0 56) (setq E0 93.6) (setq m0 45.9))
       ((= D0 64) (setq E0 104.9) (setq m0 52.4))
       ((= d0 4) (setq e0 7.7) (setq m0 3.2))
)
  (SETQ D(* d0 sc))
  (setq e(* e0 sc))
  (setq m(* m0 sc))
  (setq H1(SQRT (- (* 2.25 (* d d)) (/ (* e e) 16))))
  (setq h(- (* 1.5 d) h1))
  (setq r1 (+ (* h h) (/ (* e e) 64)))
  (setq r (/ (/ r1 2) h))
  (setq P1 (list (/ e 2) (- m h)))
  (setq p2 (list (/ e 4) (- m h)))
  (setq c1 (list (* 0.375 E) (- m r)))
  (command "ucs" "o" o)
  (command "ucs" "z" ang)
  (command "arc" p1 "c" c1 p2)
  (setq P3 (list (/ e 4) h))
  (setq p4 (list (/ e 2) h))
  (setq C2 (list (* 0.375 e) r))
  (command "arc" p3 "c" c2 p4)
  (setq p5 (list (- 0 (/ e 4)) (- m h)))
  (setq p6 (list (- 0 (/ e 2)) (- m h)))
  (setq c3 (list (- 0 (* 0.375 e)) (- m r)))
  (command "arc" p5 "c" c3 p6)
  (setq p7 (list (- 0 (/ e 2)) h)) 
  (setq p8 (list (- 0 (/ e 4)) h)) 
  (setq c4 (list (- 0 (* 0.375 e)) r))
  (command "arc" p7 "c" c4 p8)
  (command "line" p1 p4 "")
  (command "line" p2 p3 "")
  (command "line" p5 p8 "")
  (command "line" p6 p7 "")
  (setq P9 (list (* 0.375 e) m))
  (setq p10 (list (- 0 (* 0.375 e)) m))
  (command "line" p9 p10 "")
  (setq p11 (list (* 0.375 e) 0))
  (setq p12 (list (- 0 (* 0.375 e)) 0))
  (command "line" p11 p12 "")
  (setq c5 (list 0 (- m (* 1.5 d))))
  (command "arc" p2 "c" c5 p5)
  (setq c6 (list 0 (* 1.5 d)))
  (command "arc" p8 "c" c6 p3)
  (command "ucs" "z" (- 0 ang))
  (command "ucs" "w")
  (command "osmode" os)
  (COMMAND "REDRAWALL")
  (COMMAND "REGEN")
  (princ)
)

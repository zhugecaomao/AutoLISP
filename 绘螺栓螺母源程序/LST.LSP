(defun C:lst()
 (setq c (getpoint "\n 输入螺栓中心点:"))
 (setq m (getreal "\n 输入螺栓规格:")) 
 (setq e (getreal "\n 输入绘图比例:"))
 (setq ang(getangle c "\n 输入旋转角度:"))
 (setq zx(getstring "\n 是否要中心线(Yes/<No>):"))
 
 (cond ((= m 6) (setq s0 10))
       ((= m 8) (setq s0 13))
       ((= m 10) (setq s0 16))
       ((= m 12) (setq s0 18))
       ((= m 16) (setq s0 24))
       ((= m 20) (setq s0 30))
       ((= m 24) (setq s0 36))
       ((= m 30) (setq s0 46))
  )   
  (setq os (getvar "osmode"))
  (command "osmode" 0)
  (setq s (* s0 e))
  (setq r (/ s 2))
  (SETQ R1 (/ R (SIN (/ PI 3))))
  (SETQ RR (+ R1 3))
  (setq P1(polar c (- ang (/ pi 2)) r))
  (command  "circle" c "d" s)
  (command "polygon" "6" c "c" p1)
  (cond ((or (= zx "y") (= zx "Y"))
        (setq zx1 (polar c (- ang 0) (+ rR 3)))
        (setq zx2 (polar c (- ang (/ pi 1)) (+ rR 3)))
        (setq zx3 (polar c (- ang (/ pi 2)) (+ rR 3)))
        (setq zx4 (polar c (- ang (* pi 1.5)) (+ rR 3)))
        (command "line" zx3 zx4 "")
        (command "line" zx1 zx2 ""))
  )
  (command "osmode" os)
  (princ)
)
